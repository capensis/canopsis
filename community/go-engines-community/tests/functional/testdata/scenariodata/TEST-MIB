TESTOBJECT-NOTIFY-MIB DEFINITIONS ::= BEGIN
  IMPORTS
    MODULE-IDENTITY,  enterprises 
      FROM SNMPv2-SMI
    MODULE-IDENTITY, OBJECT-TYPE,  NOTIFICATION-TYPE, Integer32
      FROM SNMPv2-SMI;

testNotify MODULE-IDENTITY
  LAST-UPDATED "202301130000Z"
  ORGANIZATION "Test"
  CONTACT-INFO
      "Test Author
      "
  DESCRIPTION
      "Objects for Test events.
      "
  REVISION "202301130000Z"
  DESCRIPTION
      "Initial Version"
	::= { enterprises 8072 9999 9999 }

testObjectEventTable OBJECT-TYPE 
  SYNTAX      SEQUENCE OF ObjectEventEntry
  MAX-ACCESS  not-accessible
  STATUS      current
  DESCRIPTION
    "Table of Object events"
  ::= { testNotify 1 }

ObjectEventEntry ::= SEQUENCE {
  tObjectEventIndex    Integer32,
  tObjectname          OCTET STRING,
  tObjectDurationSec   Integer32
  }
  
testObjectEventEntry  OBJECT-TYPE
  SYNTAX      ObjectEventEntry
  MAX-ACCESS  not-accessible
  STATUS      current
  DESCRIPTION
    "Each notification event"
  INDEX { tObjectEventIndex }
  ::= { testObjectEventTable 1 }
  
tObjectEventIndex OBJECT-TYPE
  SYNTAX     Integer32 (1..65535)
  MAX-ACCESS not-accessible
  STATUS     current
  DESCRIPTION 
    "This object uniquely identifies event entry.  It's generated by the SNMP 
    application and is not related to SNMP source of data."
  ::= { testObjectEventEntry 1 }

tObjectname    OBJECT-TYPE
  SYNTAX     OCTET STRING
  MAX-ACCESS read-only
  STATUS     current
  DESCRIPTION 
    "Object's name according with configuration."
  ::= { testObjectEventEntry 2 }

tObjectDurationSec   OBJECT-TYPE
  SYNTAX     Integer32
  MAX-ACCESS read-only
  STATUS     current
  DESCRIPTION
   "A number indicating the number of seconds that the object has spent in its 
   current state"
  ::= { testObjectEventEntry 3 }


--
-- Events and Notifications
--

tObjectEvent  NOTIFICATION-TYPE
  OBJECTS { tObjectname, tObjectDurationSec }
  STATUS  current
  DESCRIPTION
    "The SNMP trap that is generated as a result of an event with object data"

  ::= { testNotify 2 }

END
