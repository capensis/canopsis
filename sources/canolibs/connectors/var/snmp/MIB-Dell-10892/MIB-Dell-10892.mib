-------------------------------------------------------------------------------
--
-- Title: Systems Management Instrumentation MIB
--
-- Version: 5.9.5
--
-- Release Date: March 2011
--
-- Description: This MIB defines MIB objects that make system instrumentation
-- data available to SNMP management applications.
--
-- Copyright (c) 2000-2011 Dell Inc.
-- All Rights Reserved.
--
-- Note: The information and functionality described by this MIB file,
-- like many MIB files, is subject to change without notice.
-- Please examine the version number of this MIB and compare it
-- to the version number you are expecting.
--
-- OID Format Legend:
--   <a> = attribute ID
--   <i> = index ID
--
-------------------------------------------------------------------------------


-------------------------------------------------------------------------------
-- Begin MIB
-------------------------------------------------------------------------------

MIB-Dell-10892 DEFINITIONS ::= BEGIN

IMPORTS
    enterprises, IpAddress
        FROM RFC1155-SMI
    OBJECT-TYPE
        FROM RFC-1212
    TRAP-TYPE
        FROM RFC-1215
    DisplayString
        FROM RFC1213-MIB;


-------------------------------------------------------------------------------
-- Object Identifiers
-------------------------------------------------------------------------------

-- Enterprise ID
dell                            OBJECT IDENTIFIER ::= { enterprises    674   }

-- Server3 Branch
server3                         OBJECT IDENTIFIER ::= { dell           10892 }

-- Server3 Groups
baseboardGroup                  OBJECT IDENTIFIER ::= { server3        1     }
-- drsOutOfBandGroup            OBJECT IDENTIFIER ::= { server3        2     }
-- (drsOutOfBandGroup is defined in another MIB file.)

-- Server3 Baseboard Groups for Instrumentation
mIBVersionGroup                 OBJECT IDENTIFIER ::= { baseboardGroup 1     }
systemManagementSoftwareGroup   OBJECT IDENTIFIER ::= { baseboardGroup 100   }
systemStateGroup                OBJECT IDENTIFIER ::= { baseboardGroup 200   }
chassisInformationGroup         OBJECT IDENTIFIER ::= { baseboardGroup 300   }
operatingSystemGroup            OBJECT IDENTIFIER ::= { baseboardGroup 400   }
systemResourceGroup             OBJECT IDENTIFIER ::= { baseboardGroup 500   }
powerGroup                      OBJECT IDENTIFIER ::= { baseboardGroup 600   }
thermalGroup                    OBJECT IDENTIFIER ::= { baseboardGroup 700   }
userSecurityGroup               OBJECT IDENTIFIER ::= { baseboardGroup 800   }
remoteFlashBIOSGroup            OBJECT IDENTIFIER ::= { baseboardGroup 900   }
portGroup                       OBJECT IDENTIFIER ::= { baseboardGroup 1000  }
deviceGroup                     OBJECT IDENTIFIER ::= { baseboardGroup 1100  }
slotGroup                       OBJECT IDENTIFIER ::= { baseboardGroup 1200  }
memoryGroup                     OBJECT IDENTIFIER ::= { baseboardGroup 1300  }
biosSetUpControlGroup           OBJECT IDENTIFIER ::= { baseboardGroup 1400  }
lraGroup                        OBJECT IDENTIFIER ::= { baseboardGroup 1500  }
cooGroup                        OBJECT IDENTIFIER ::= { baseboardGroup 1600  }
-- remoteAccessGroup            OBJECT IDENTIFIER ::= { baseboardGroup 1700  }
-- (remoteAccessGroup is defined in dcs3rmt.mib)
clusterGroup                    OBJECT IDENTIFIER ::= { baseboardGroup 1800  }
bmcGroup                        OBJECT IDENTIFIER ::= { baseboardGroup 1900  }
-- fruGroup                     OBJECT IDENTIFIER ::= { baseboardGroup 2000  }
-- (fruGroup is defined in dcs3fru.mib)
alertGroup                      OBJECT IDENTIFIER ::= { baseboardGroup 5000  }


-------------------------------------------------------------------------------
-- Textual Conventions
-------------------------------------------------------------------------------

DellString                      ::= DisplayString (SIZE (0..64))
DellSecurityString              ::= DisplayString (SIZE (0..255))
DellCostofOwnershipString       ::= DisplayString (SIZE (0..64))
DellMACAddress                  ::= OCTET STRING (SIZE(6))
DellObjectRange                 ::= INTEGER (1..128)
DellUnsigned8BitRange           ::= INTEGER (0..255)
DellUnsigned16BitRange          ::= INTEGER (0..65535)
DellUnsigned32BitRange          ::= INTEGER (0..4294967295)
DellSigned32BitRange            ::= INTEGER (-2147483647..2147483647)
DellBoolean                     ::= INTEGER (0..1)    -- 0 = FALSE, 1 = TRUE

-- This definition is required because SNMP V1 does not support 64 bit ranges.
-- The information sent back by this subagent will have the most significant
-- byte of the information as the first byte (i.e. network byte order).
-- E.G. The integer value 0x1029384754657687 will be sent as:
-- Byte:   1         2         3         4         ...
-- Hex:    10        29        38        47        ...
-- Binary: 0001 0000 0010 1001 0011 1000 0100 0111 ...
DellUnsigned64BitRange          ::= OCTET STRING (SIZE(8))

-- DellDateName dates are defined in the displayable format
--   yyyymmddHHMMSS.uuuuuu+ooo
-- where yyyy is the year, mm is the month number, dd is the day of the month,
-- HHMMSS are the hours, minutes and seconds, respectively, uuuuuu is the
-- number of microseconds, and +ooo is the offset from UTC in minutes. If east
-- of UTC, the number is preceded by a plus (+) sign, and if west of UTC, the
-- number is preceded by a minus (-) sign.
--
-- For example, Wednesday, May 25, 1994, at 1:30:15 PM EDT
--   would be represented as: 19940525133015.000000-300
--
-- Values must be zero-padded if necessary, like "05" in the example above.
-- If a value is not supplied for a field, each character in the field
-- must be replaced with asterisk ('*') characters.
DellDateName                    ::= DisplayString (SIZE (25))

-- Note About Bit Fields:
-- Attributes with definitions of xxxCapabilities, xxxCapabilitiesUnique,
-- xxxSettings, xxxSettingsUnique and xxxFeatureFlags are integers
-- representing a series of bit definitions.  They are NOT enumerations and
-- should be treated as bit fields.  The value is passed as a decimal value;
-- it should be converted to hex, and the appropriate bits should be parsed
-- from that.  Some of the more common bit combinations are defined in some
-- variables, but not all combinations are or will be defined.

--
-- Generic State Capabilities
--
DellStateCapabilities           ::= INTEGER {
    -- If set to 0 (zero), object has no state capabilities
    unknownCapabilities(1),     -- object's state capabilities are unknown
    -- The object's state capabilities allow it to be set to:
    enableCapable(2),           -- be disabled (offline) or be enabled (online)
    notReadyCapable(4),         -- not ready
    enableAndNotReadyCapable(6)
}

--
-- Generic State Settings
--
DellStateSettings           ::= INTEGER {
    -- If set to 0 (zero), object has no state settings enabled and is disabled
    unknown(1),             -- object's state is unknown
    enabled(2),             -- object's state is disabled (offline) if bit is off
                            -- or enabled (online) if bit is on
    notReady(4),            -- object's state is not ready
    enabledAndNotReady(6)
}

--
-- Probe Capabilities
--
DellProbeCapabilities                           ::= INTEGER {
    -- If set to 0 (zero) the object has no probe capabilities
    -- The object's probe capabilities allow it to be set to:
    upperNonCriticalThresholdSetCapable(1),     -- upper noncritical threshold can be set
    lowerNonCriticalThresholdSetCapable(2),     -- lower noncritical threshold can be set
    upperNonCriticalThresholdDefaultCapable(4), -- upper noncritical threshold can be set to default
    lowerNonCriticalThresholdDefaultCapable(8)  -- lower noncritical threshold can be set to default
}

--
-- Status
--
DellStatus                  ::= INTEGER {
    other(1),               -- status is not one of the following:
    unknown(2),             -- status of object is unknown (not known or monitored)
    ok(3),                  -- status of object is OK (normal)
    nonCritical(4),         -- status of object is noncritical (warning)
    critical(5),            -- status of object is critical (failure)
    nonRecoverable(6)       -- status of object is non-recoverable (dead)
}

--
-- Redundancy Status
--
DellStatusRedundancy        ::= INTEGER {
    other(1),               -- redundancy status is not one of the following:
    unknown(2),             -- redundancy status is unknown (not known or monitored)
    full(3),                -- object is fully redundant
    degraded(4),            -- object's redundancy has been degraded
    lost(5),                -- object's redundancy has been lost
    notRedundant(6),        -- redundancy status does not apply or object is not redundant
    redundancyOffline(7)    -- redundancy object taken offline
}

--
-- Probe Status
--
DellStatusProbe             ::= INTEGER {
    other(1),               -- probe status is not one of the following:
    unknown(2),             -- probe status is unknown (not known or monitored)
    ok(3),                  -- probe is reporting a value within the thresholds
    nonCriticalUpper(4),    -- probe has crossed upper noncritical threshold
    criticalUpper(5),       -- probe has crossed upper critical threshold
    nonRecoverableUpper(6), -- probe has crossed upper non-recoverable threshold
    nonCriticalLower(7),    -- probe has crossed lower noncritical threshold
    criticalLower(8),       -- probe has crossed lower critical threshold
    nonRecoverableLower(9), -- probe has crossed lower non-recoverable threshold
    failed(10)              -- probe is not functional
}


-------------------------------------------------------------------------------
--
-- MIB Groups
--
-------------------------------------------------------------------------------


-------------------------------------------------------------------------------
-- MIB Version Group
--
-- OID Format: 1.3.6.1.4.1.674.10892.1.1.<a>.0
-------------------------------------------------------------------------------

mIBMajorVersionNumber                           OBJECT-TYPE
    SYNTAX      DellUnsigned8BitRange
    ACCESS      read-only
    STATUS      mandatory
    DESCRIPTION
"0001.0001 This attribute defines the major version number for the version
of this MIB supported by the systems management software."
    ::= { mIBVersionGroup 1 }
mIBMinorVersionNumber                           OBJECT-TYPE
    SYNTAX      DellUnsigned8BitRange
    ACCESS      read-only
    STATUS      mandatory
    DESCRIPTION
"0001.0002 This attribute defines the minor version number for the version
of this MIB supported by the systems management software."
    ::= { mIBVersionGroup 2 }
mIBMaintenanceVersionNumber                     OBJECT-TYPE
    SYNTAX      DellUnsigned8BitRange
    ACCESS      read-only
    STATUS      mandatory
    DESCRIPTION
"0001.0003 This attribute defines the maintenance version number for the
version of this MIB supported by the systems management software."
    ::= { mIBVersionGroup 3 }


-------------------------------------------------------------------------------
-- System Management Software Group
--
-- OID Format: 1.3.6.1.4.1.674.10892.1.100.<a>.0
-------------------------------------------------------------------------------

SMSSupportedTypes                               ::= INTEGER {
    -- Note: These values are bit masks, so combination values are possible.
    supportsSNMP(1),                            -- supports SNMP
    supportsDMI(2),                             -- supports DMI
    supportsSNMPandDMI(3),                      -- supports SNMP and DMI
    supportsCIMOM(4),                           -- supports CIM
    supportsSNMPandCIMOM(5),                    -- supports SNMP and CIM
    supportsSNMPandDMIandCIMOM(7)               -- supports SNMP, DMI and CIM
}
SMSFeatureFlags                                 ::= INTEGER {
    -- Note: These values are bit masks, so combination values are possible.
    -- If 0 (zero), none of the following features are enabled:
    webOneToOneManagementPreferred(1)           -- web 1:1 management preferred
}
SMSSNMPAgentFeatureFlags                        ::= INTEGER {
    -- Note: These values are bit masks, so combination values are possible.
    -- If 0 (zero), none of the following features are enabled:
    supportsSparseTables(1)                     -- SNMP agent supports sparse tables
}

systemManagementSoftwareName                    OBJECT-TYPE
    SYNTAX      DellString
    ACCESS      read-only
    STATUS      mandatory
    DESCRIPTION
"0100.0001 This attribute defines the product name of the
systems management software."
    ::= { systemManagementSoftwareGroup 1 }
systemManagementSoftwareVersionNumberName       OBJECT-TYPE
    SYNTAX      DellString
    ACCESS      read-only
    STATUS      mandatory
    DESCRIPTION
"0100.0002 This attribute defines the version number of the
instrumentation component of the systems management software."
    ::= { systemManagementSoftwareGroup 2 }
systemManagementSoftwareBuildNumber             OBJECT-TYPE
    SYNTAX      DellUnsigned16BitRange
    ACCESS      read-only
    STATUS      mandatory
    DESCRIPTION
"0100.0003 This attribute defines the build number of the
instrumentation component of the systems management software."
    ::= { systemManagementSoftwareGroup 3 }
systemManagementSoftwareDescriptionName         OBJECT-TYPE
    SYNTAX      DellString
    ACCESS      read-only
    STATUS      mandatory
    DESCRIPTION
"0100.0004 This attribute defines the description of the
systems management software."
    ::= { systemManagementSoftwareGroup 4 }
systemManagementSoftwareSupportedProtocol       OBJECT-TYPE
    SYNTAX      SMSSupportedTypes
    ACCESS      read-only
    STATUS      mandatory
    DESCRIPTION
"0100.0005 This attribute defines the protocols supported by the
instrumentation component of the systems management software."
    ::= { systemManagementSoftwareGroup 5 }
systemManagementSoftwarePreferredProtocol       OBJECT-TYPE
    SYNTAX      SMSSupportedTypes
    ACCESS      read-only
    STATUS      mandatory
    DESCRIPTION
"0100.0006 This attribute defines the protocol preferred by the
instrumentation component of the systems management software."
    ::= { systemManagementSoftwareGroup 6 }
systemManagementSoftwareUpdateLevelName         OBJECT-TYPE
    SYNTAX      DellString
    ACCESS      read-only
    STATUS      mandatory
    DESCRIPTION
"0100.0007 This attribute defines the update level of the
instrumentation component of the systems management software."
    ::= { systemManagementSoftwareGroup 7 }
systemManagementSoftwareURLName                 OBJECT-TYPE
    SYNTAX      DisplayString (SIZE (0..1024))
    ACCESS      read-only
    STATUS      mandatory
    DESCRIPTION
"0100.0008 This attribute defines the Universal Resource Locator (URL)
of the systems management software."
    ::= { systemManagementSoftwareGroup 8 }
systemManagementSoftwareLanguageName            OBJECT-TYPE
    SYNTAX      DisplayString (SIZE (0..255))
    ACCESS      read-only
    STATUS      mandatory
    DESCRIPTION
"0100.0009 This attribute defines the language of the
systems management software."
    ::= { systemManagementSoftwareGroup 9 }
systemManagementSoftwareGlobalVersionName       OBJECT-TYPE
    SYNTAX      DellString
    ACCESS      read-only
    STATUS      mandatory
    DESCRIPTION
"0100.0010 This attribute defines the global version of the
systems management software."
    ::= { systemManagementSoftwareGroup 10 }
systemManagementSoftwareFeatureFlags            OBJECT-TYPE
    SYNTAX      SMSFeatureFlags
    ACCESS      read-only
    STATUS      mandatory
    DESCRIPTION
"0100.0011 This attribute defines the features of the systems management
software.  If the value is zero, none of the features are enabled.
Note: This attribute is a bit field, so the value returned may be
a combination of the bit masks defined in SMSFeatureFlags."
    ::= { systemManagementSoftwareGroup 11 }
systemManagementSoftwareSNMPAgentFeatureFlags   OBJECT-TYPE
    SYNTAX      SMSSNMPAgentFeatureFlags
    ACCESS      read-only
    STATUS      mandatory
    DESCRIPTION
"0100.0012 This attribute defines the features of the SNMP agent
software provided by the operating system.  If the value is zero,
none of the features are enabled.  Note: This attribute is a bit field,
so the value returned may be a combination of the bit masks defined
in SMSSNMPAgentFeatureFlags."
    ::= { systemManagementSoftwareGroup 12 }
systemManagementSoftwareManufacturerName        OBJECT-TYPE
    SYNTAX      DellString
    ACCESS      read-only
    STATUS      mandatory
    DESCRIPTION
"0100.0013 This attribute defines the manufacturer of the
systems management software."
    ::= { systemManagementSoftwareGroup 13 }


-------------------------------------------------------------------------------
-- System State Group
--
-- OID Format: 1.3.6.1.4.1.674.10892.1.200
-------------------------------------------------------------------------------


-------------------------------------------------------------------------------
-- System State Table
--
-- OID Format: 1.3.6.1.4.1.674.10892.1.200.10.1.<a>.<i1>
-------------------------------------------------------------------------------

SystemStateTableEntry                              ::= SEQUENCE {
    systemStatechassisIndex                        DellObjectRange,
    systemStateGlobalSystemStatus                  DellStatus,
    systemStateChassisState                        DellStateSettings,
    systemStateChassisStatus                       DellStatus,
    systemStatePowerUnitStateDetails               OCTET STRING (SIZE(1..128)),
    systemStatePowerUnitStatusRedundancy           DellStatusRedundancy,
    systemStatePowerUnitStatusDetails              OCTET STRING (SIZE(1..128)),
    systemStatePowerSupplyStateDetails             OCTET STRING (SIZE(1..128)),
    systemStatePowerSupplyStatusCombined           DellStatus,
    systemStatePowerSupplyStatusDetails            OCTET STRING (SIZE(1..128)),
    systemStateVoltageStateDetails                 OCTET STRING (SIZE(1..128)),
    systemStateVoltageStatusCombined               DellStatus,
    systemStateVoltageStatusDetails                OCTET STRING (SIZE(1..128)),
    systemStateAmperageStateDetails                OCTET STRING (SIZE(1..128)),
    systemStateAmperageStatusCombined              DellStatus,
    systemStateAmperageStatusDetails               OCTET STRING (SIZE(1..128)),
    systemStateCoolingUnitStateDetails             OCTET STRING (SIZE(1..128)),
    systemStateCoolingUnitStatusRedundancy         DellStatusRedundancy,
    systemStateCoolingUnitStatusDetails            OCTET STRING (SIZE(1..128)),
    systemStateCoolingDeviceStateDetails           OCTET STRING (SIZE(1..128)),
    systemStateCoolingDeviceStatusCombined         DellStatus,
    systemStateCoolingDeviceStatusDetails          OCTET STRING (SIZE(1..128)),
    systemStateTemperatureStateDetails             OCTET STRING (SIZE(1..128)),
    systemStateTemperatureStatusCombined           DellStatus,
    systemStateTemperatureStatusDetails            OCTET STRING (SIZE(1..128)),
    systemStateMemoryDeviceStateDetails            OCTET STRING (SIZE(1..128)),
    systemStateMemoryDeviceStatusCombined          DellStatus,
    systemStateMemoryDeviceStatusDetails           OCTET STRING (SIZE(1..128)),
    systemStateChassisIntrusionStateDetails        OCTET STRING (SIZE(1..128)),
    systemStateChassisIntrusionStatusCombined      DellStatus,
    systemStateChassisIntrusionStatusDetails       OCTET STRING (SIZE(1..128)),
    systemStateACPowerSwitchStateDetails           OCTET STRING (SIZE(1..128)),
    systemStateACPowerSwitchStatusRedundancy       DellStatusRedundancy,
    systemStateACPowerSwitchStatusDetails          OCTET STRING (SIZE(1..128)),
    systemStateACPowerCordStateDetails             OCTET STRING (SIZE(1..128)),
    systemStateACPowerCordStatusCombined           DellStatus,
    systemStateACPowerCordStatusDetails            OCTET STRING (SIZE(1..128)),
    systemStateRedundantMemoryUnitStateDetails     OCTET STRING (SIZE(1..128)),
    systemStateRedundantMemoryUnitStatusRedundancy DellStatusRedundancy,
    systemStateRedundantMemoryUnitStatusDetails    OCTET STRING (SIZE(1..128)),
    systemStateEventLogStatus                      DellStatus,
    systemStatePowerUnitStatusCombined             DellStatus,
    systemStatePowerUnitStatusList                 OCTET STRING (SIZE(1..128)),
    systemStateCoolingUnitStatusCombined           DellStatus,
    systemStateCoolingUnitStatusList               OCTET STRING (SIZE(1..128)),
    systemStateACPowerSwitchStatusCombined         DellStatus,
    systemStateACPowerSwitchStatusList             OCTET STRING (SIZE(1..128)),
    systemStateRedundantMemoryUnitStatusCombined   DellStatus,
    systemStateRedundantMemoryUnitStatusList       OCTET STRING (SIZE(1..128)),
    systemStateProcessorDeviceStatusCombined       DellStatus,
    systemStateProcessorDeviceStatusList           OCTET STRING (SIZE(1..128)),
    systemStateBatteryStatusCombined               DellStatus,
    systemStateBatteryStatusList                   OCTET STRING (SIZE(1..128)),
    systemStateSDCardUnitStatusCombined            DellStatus,
    systemStateSDCardUnitStatusList                OCTET STRING (SIZE(1..128)),
    systemStateSDCardDeviceStatusCombined          DellStatus,
    systemStateSDCardDeviceStatusList              OCTET STRING (SIZE(1..128))
}

systemStateTable                                OBJECT-TYPE
    SYNTAX      SEQUENCE OF SystemStateTableEntry
    ACCESS      not-accessible
    STATUS      mandatory
    DESCRIPTION
"0200.0010 This object defines the System State Table."
    ::= { systemStateGroup 10 }
systemStateTableEntry                           OBJECT-TYPE
    SYNTAX      SystemStateTableEntry
    ACCESS      not-accessible
    STATUS      mandatory
    DESCRIPTION
"0200.0010.0001 This object defines the System State Table Entry."
    INDEX       { systemStatechassisIndex }
    ::= { systemStateTable 1 }

systemStatechassisIndex                         OBJECT-TYPE
    SYNTAX      DellObjectRange
    ACCESS      read-only
    STATUS      mandatory
    DESCRIPTION
"0200.0010.0001.0001 This attribute defines the index (one based) of this
chassis."
    ::= { systemStateTableEntry 1 }
systemStateGlobalSystemStatus                   OBJECT-TYPE
    SYNTAX      DellStatus
    ACCESS      read-only
    STATUS      mandatory
    DESCRIPTION
"0200.0010.0001.0002 This attribute defines the global system status
of all chassis being monitored by the systems management software."
    ::= { systemStateTableEntry 2 }
systemStateChassisState                         OBJECT-TYPE
    SYNTAX      DellStateSettings
    ACCESS      read-only
    STATUS      mandatory
    DESCRIPTION
"0200.0010.0001.0003 This attribute defines the state settings of this
chassis."
    ::= { systemStateTableEntry 3 }
systemStateChassisStatus                        OBJECT-TYPE
    SYNTAX      DellStatus
    ACCESS      read-only
    STATUS      mandatory
    DESCRIPTION
"0200.0010.0001.0004 This attribute defines the status of this chassis."
    ::= { systemStateTableEntry 4 }
systemStatePowerUnitStateDetails                OBJECT-TYPE
    SYNTAX      OCTET STRING (SIZE(1..128))
    ACCESS      read-only
    STATUS      mandatory
    DESCRIPTION
"0200.0010.0001.0005 This attribute lists the state settings of each
power unit of this chassis.  The results are returned as a binary octet
string where each byte of the octet string represents the state settings
of a power unit.  The first byte returned represents the state settings
of the first power unit, etc.  The bytes have the same definition type
as DellStateSettings."
    ::= { systemStateTableEntry 5 }
systemStatePowerUnitStatusRedundancy            OBJECT-TYPE
    SYNTAX      DellStatusRedundancy
    ACCESS      read-only
    STATUS      mandatory
    DESCRIPTION
"0200.0010.0001.0006 This attribute defines the combined redundancy status
of all power units of this chassis."
    ::= { systemStateTableEntry 6 }
systemStatePowerUnitStatusDetails               OBJECT-TYPE
    SYNTAX      OCTET STRING (SIZE(1..128))
    ACCESS      read-only
    STATUS      mandatory
    DESCRIPTION
"0200.0010.0001.0007 This attribute lists the redundancy status of each
power unit of this chassis.  The results are returned as a binary octet
string where each byte of the octet string represents the redundancy status
of a power unit.  The first byte returned represents the redundancy status
of the first power unit, etc.  The bytes have the same definition type as
DellStatusRedundancy."
    ::= { systemStateTableEntry 7 }
systemStatePowerSupplyStateDetails              OBJECT-TYPE
    SYNTAX      OCTET STRING (SIZE(1..128))
    ACCESS      read-only
    STATUS      mandatory
    DESCRIPTION
"0200.0010.0001.0008 This attribute lists the state settings of each
power supply of this chassis.  The results are returned as a binary octet
string where each byte of the octet string represents the state settings
of a power supply.  The first byte returned represents the state settings
of the first power supply, etc.  The bytes have the same definition type
as DellStateSettings."
    ::= { systemStateTableEntry 8 }
systemStatePowerSupplyStatusCombined            OBJECT-TYPE
    SYNTAX      DellStatus
    ACCESS      read-only
    STATUS      mandatory
    DESCRIPTION
"0200.0010.0001.0009 This attribute defines the combined status of all
power supplies of this chassis."
    ::= { systemStateTableEntry 9 }
systemStatePowerSupplyStatusDetails             OBJECT-TYPE
    SYNTAX      OCTET STRING (SIZE(1..128))
    ACCESS      read-only
    STATUS      mandatory
    DESCRIPTION
"0200.0010.0001.0010 This attribute lists the status of each power supply
of this chassis.  The results are returned as a binary octet string where
each byte of the octet string represents the status of a power supply.
The first byte returned represents the status of the first power supply,
etc.  The bytes have the same definition type as DellStatus."
    ::= { systemStateTableEntry 10 }
systemStateVoltageStateDetails                  OBJECT-TYPE
    SYNTAX      OCTET STRING (SIZE(1..128))
    ACCESS      read-only
    STATUS      mandatory
    DESCRIPTION
"0200.0010.0001.0011 This attribute lists the state settings of each
voltage probe of this chassis.  The results are returned as a binary octet
string where each byte of the octet string represents the state settings
of a voltage probe.  The first byte returned represents the state settings
of the first voltage probe, etc.  The bytes have the same definition type
as DellStateSettings."
    ::= { systemStateTableEntry 11 }
systemStateVoltageStatusCombined                OBJECT-TYPE
    SYNTAX      DellStatus
    ACCESS      read-only
    STATUS      mandatory
    DESCRIPTION
"0200.0010.0001.0012 This attribute defines the combined status of all
voltage probes of this chassis."
    ::= { systemStateTableEntry 12 }
systemStateVoltageStatusDetails                 OBJECT-TYPE
    SYNTAX      OCTET STRING (SIZE(1..128))
    ACCESS      read-only
    STATUS      mandatory
    DESCRIPTION
"0200.0010.0001.0013 This attribute lists the status of each voltage probe
of this chassis.  The results are returned as a binary octet string where
each byte of the octet string represents the status of a voltage probe.
The first byte returned represents the status of the first voltage probe,
etc.  The bytes have the same definition type as DellStatus."
    ::= { systemStateTableEntry 13 }
systemStateAmperageStateDetails                 OBJECT-TYPE
    SYNTAX      OCTET STRING (SIZE(1..128))
    ACCESS      read-only
    STATUS      mandatory
    DESCRIPTION
"0200.0010.0001.0014 This attribute lists the state settings of each
amperage probe of this chassis.  The results are returned as a binary octet
string where each byte of the octet string represents the state settings
of an amperage probe.  The first byte returned represents the state settings
of the first amperage probe, etc.  The bytes have the same definition type
as DellStateSettings."
    ::= { systemStateTableEntry 14 }
systemStateAmperageStatusCombined               OBJECT-TYPE
    SYNTAX      DellStatus
    ACCESS      read-only
    STATUS      mandatory
    DESCRIPTION
"0200.0010.0001.0015 This attribute defines the combined status of all
amperage probes of this chassis."
    ::= { systemStateTableEntry 15 }
systemStateAmperageStatusDetails                OBJECT-TYPE
    SYNTAX      OCTET STRING (SIZE(1..128))
    ACCESS      read-only
    STATUS      mandatory
    DESCRIPTION
"0200.0010.0001.0016 This attribute lists the status of each amperage probe
of this chassis.  The results are returned as a binary octet string where
each byte of the octet string represents the status of an amperage probe.
The first byte returned represents the status of the first amperage probe,
etc.  The bytes have the same definition type as DellStatus."
    ::= { systemStateTableEntry 16 }
systemStateCoolingUnitStateDetails              OBJECT-TYPE
    SYNTAX      OCTET STRING (SIZE(1..128))
    ACCESS      read-only
    STATUS      mandatory
    DESCRIPTION
"0200.0010.0001.0017 This attribute lists the state settings of each
cooling unit of this chassis.  The results are returned as a binary octet
string where each byte of the octet string represents the state settings
of a cooling unit.  The first byte returned represents the state settings
of the first cooling unit, etc.  The bytes have the same definition type
as DellStateSettings."
    ::= { systemStateTableEntry 17 }
systemStateCoolingUnitStatusRedundancy          OBJECT-TYPE
    SYNTAX      DellStatusRedundancy
    ACCESS      read-only
    STATUS      mandatory
    DESCRIPTION
"0200.0010.0001.0018 This attribute defines the combined redundancy status
of all cooling units of this chassis."
    ::= { systemStateTableEntry 18 }
systemStateCoolingUnitStatusDetails             OBJECT-TYPE
    SYNTAX      OCTET STRING (SIZE(1..128))
    ACCESS      read-only    STATUS      mandatory
    DESCRIPTION
"0200.0010.0001.0019 This attribute lists the redundancy status of each
cooling unit of this chassis.  The results are returned as a binary octet
string where each byte of the octet string represents the redundancy status
of a cooling unit.  The first byte returned represents the redundancy status
of the first cooling unit, etc.  The bytes have the same definition type as
DellStatusRedundancy."
    ::= { systemStateTableEntry 19 }
systemStateCoolingDeviceStateDetails            OBJECT-TYPE
    SYNTAX      OCTET STRING (SIZE(1..128))
    ACCESS      read-only
    STATUS      mandatory
    DESCRIPTION
"0200.0010.0001.0020 This attribute lists the state settings of each
cooling device of this chassis.  The results are returned as a binary octet
string where each byte of the octet string represents the state settings
of a cooling device.  The first byte returned represents the state settings
of the first cooling device, etc.  The bytes have the same definition type
as DellStateSettings."
    ::= { systemStateTableEntry 20 }
systemStateCoolingDeviceStatusCombined          OBJECT-TYPE
    SYNTAX      DellStatus
    ACCESS      read-only
    STATUS      mandatory
    DESCRIPTION
"0200.0010.0001.0021 This attribute defines the combined status of all
cooling devices of this chassis."
    ::= { systemStateTableEntry 21 }
systemStateCoolingDeviceStatusDetails           OBJECT-TYPE
    SYNTAX      OCTET STRING (SIZE(1..128))
    ACCESS      read-only
    STATUS      mandatory
    DESCRIPTION
"0200.0010.0001.0022 This attribute lists the status of each cooling device
of this chassis.  The results are returned as a binary octet string where
each byte of the octet string represents the status of a cooling device.
The first byte returned represents the status of the first cooling device,
etc.  The bytes have the same definition type as DellStatus."
    ::= { systemStateTableEntry 22 }
systemStateTemperatureStateDetails              OBJECT-TYPE
    SYNTAX      OCTET STRING (SIZE(1..128))
    ACCESS      read-only
    STATUS      mandatory
    DESCRIPTION
"0200.0010.0001.0023 This attribute lists the state settings of each
temperature probe of this chassis.  The results are returned as a binary octet
string where each byte of the octet string represents the state settings
of a temperature probe.  The first byte returned represents the state settings
of the first temperature probe, etc.  The bytes have the same definition type
as DellStateSettings."
    ::= { systemStateTableEntry 23 }
systemStateTemperatureStatusCombined            OBJECT-TYPE
    SYNTAX      DellStatus
    ACCESS      read-only
    STATUS      mandatory
    DESCRIPTION
"0200.0010.0001.0024 This attribute defines the combined status of all
temperature probes of this chassis."
    ::= { systemStateTableEntry 24 }
systemStateTemperatureStatusDetails             OBJECT-TYPE
    SYNTAX      OCTET STRING (SIZE(1..128))
    ACCESS      read-only
    STATUS      mandatory
    DESCRIPTION
"0200.0010.0001.0025 This attribute lists the status of each temperature probe
of this chassis.  The results are returned as a binary octet string where
each byte of the octet string represents the status of a temperature probe.
The first byte returned represents the status of the first temperature probe,
etc.  The bytes have the same definition type as DellStatus."
    ::= { systemStateTableEntry 25 }
systemStateMemoryDeviceStateDetails             OBJECT-TYPE
    SYNTAX      OCTET STRING (SIZE(1..128))
    ACCESS      read-only
    STATUS      mandatory
    DESCRIPTION
"0200.0010.0001.0026 This attribute lists the state settings of each
memory device of this chassis.  The results are returned as a binary octet
string where each byte of the octet string represents the state settings
of a memory device.  The first byte returned represents the state settings
of the first memory device, etc.  The bytes have the same definition type
as DellStateSettings."
    ::= { systemStateTableEntry 26 }
systemStateMemoryDeviceStatusCombined           OBJECT-TYPE
    SYNTAX      DellStatus
    ACCESS      read-only
    STATUS      mandatory
    DESCRIPTION
"0200.0010.0001.0027 This attribute defines the combined status of all
memory devices of this chassis."
    ::= { systemStateTableEntry 27 }
systemStateMemoryDeviceStatusDetails            OBJECT-TYPE
    SYNTAX      OCTET STRING (SIZE(1..128))
    ACCESS      read-only
    STATUS      mandatory
    DESCRIPTION
"0200.0010.0001.0028 This attribute lists the status of each memory device
of this chassis.  The results are returned as a binary octet string where
each byte of the octet string represents the status of a memory device.
The first byte returned represents the status of the first memory device,
etc.  The bytes have the same definition type as DellStatus."
    ::= { systemStateTableEntry 28 }
systemStateChassisIntrusionStateDetails         OBJECT-TYPE
    SYNTAX      OCTET STRING (SIZE(1..128))
    ACCESS      read-only
    STATUS      mandatory
    DESCRIPTION
"0200.0010.0001.0029 This attribute lists the state settings of each
intrusion detection device of this chassis.  The results are returned as
a binary octet string where each byte of the octet string represents the
state settings of an intrusion detection device.  The first byte returned
represents the state settings of the first intrusion detection device, etc.
The bytes have the same definition type as DellStateSettings."
    ::= { systemStateTableEntry 29 }
systemStateChassisIntrusionStatusCombined       OBJECT-TYPE
    SYNTAX      DellStatus
    ACCESS      read-only
    STATUS      mandatory
    DESCRIPTION
"0200.0010.0001.0030 This attribute defines the combined status of all
intrusion detection devices of this chassis."
    ::= { systemStateTableEntry 30 }
systemStateChassisIntrusionStatusDetails        OBJECT-TYPE
    SYNTAX      OCTET STRING (SIZE(1..128))
    ACCESS      read-only
    STATUS      mandatory
    DESCRIPTION
"0200.0010.0001.0031 This attribute lists the status of each intrusion
detection device of this chassis.  The results are returned as a binary
octet string where each byte of the octet string represents the status
of an intrusion detection device.  The first byte returned represents the
status of the first intrusion detection device, etc.  The bytes have the
same definition type as DellStatus."
    ::= { systemStateTableEntry 31 }
systemStateACPowerSwitchStateDetails            OBJECT-TYPE
    SYNTAX      OCTET STRING (SIZE(1..128))
    ACCESS      read-only
    STATUS      mandatory
    DESCRIPTION
"0200.0010.0001.0032 This attribute lists the state settings of each
AC power switch of this chassis.  The results are returned as a binary octet
string where each byte of the octet string represents the state settings
of an AC power switch.  The first byte returned represents the state settings
of the first AC power switch, etc.  The bytes have the same definition type
as DellStateSettings."
    ::= { systemStateTableEntry 32 }
systemStateACPowerSwitchStatusRedundancy        OBJECT-TYPE
    SYNTAX      DellStatusRedundancy
    ACCESS      read-only
    STATUS      mandatory
    DESCRIPTION
"0200.0010.0001.0033 This attribute defines the combined redundancy status
of all AC power switches of this chassis."
    ::= { systemStateTableEntry 33 }
systemStateACPowerSwitchStatusDetails           OBJECT-TYPE
    SYNTAX      OCTET STRING (SIZE(1..128))
    ACCESS      read-only
    STATUS      mandatory
    DESCRIPTION
"0200.0010.0001.0034 This attribute lists the redundancy status of each
AC power switch of this chassis.  The results are returned as a binary octet
string where each byte of the octet string represents the redundancy status
of an AC power switch.  The first byte returned represents the redundancy
status of the first AC power switch, etc.  The bytes have the same definition
type as DellStatusRedundancy."
    ::= { systemStateTableEntry 34 }
systemStateACPowerCordStateDetails              OBJECT-TYPE
    SYNTAX      OCTET STRING (SIZE(1..128))
    ACCESS      read-only
    STATUS      mandatory
    DESCRIPTION
"0200.0010.0001.0035 This attribute lists the state settings of each
AC power cord associated with an AC power switch of this chassis.
The results are returned as a binary octet string where each byte of
the octet string represents the state settings of an AC power cord.
The first byte returned represents the state settings of the first
AC power cord, etc.  The bytes have the same definition type as
DellStateSettings."
    ::= { systemStateTableEntry 35 }
systemStateACPowerCordStatusCombined            OBJECT-TYPE
    SYNTAX      DellStatus
    ACCESS      read-only
    STATUS      mandatory
    DESCRIPTION
"0200.0010.0001.0036 This attribute defines the combined status of all
AC power cords for any AC power switches of this chassis."
    ::= { systemStateTableEntry 36 }
systemStateACPowerCordStatusDetails             OBJECT-TYPE
    SYNTAX      OCTET STRING (SIZE(1..128))
    ACCESS      read-only
    STATUS      mandatory
    DESCRIPTION
"0200.0010.0001.0037 This attribute lists the status of each AC power cord
associated with an AC power switch of this chassis.  The results are returned
as a binary octet string where each byte of the octet string represents
the status of an AC power cord.  The first byte returned represents the status
of the first AC power cord, etc.  The bytes have the same definition type
as DellStatus."
    ::= { systemStateTableEntry 37 }
systemStateRedundantMemoryUnitStateDetails      OBJECT-TYPE
    SYNTAX      OCTET STRING (SIZE(1..128))
    ACCESS      read-only
    STATUS      mandatory
    DESCRIPTION
"0200.0010.0001.0038 This attribute lists the state settings of each
redundant memory unit of this chassis.  The results are returned as
a binary octet string where each byte of the octet string represents
the state settings of a redundant memory unit.  The first byte returned
represents the state settings of the first redundant memory unit, etc.
The bytes have the same definition type as DellStateSettings."
    ::= { systemStateTableEntry 38 }
systemStateRedundantMemoryUnitStatusRedundancy  OBJECT-TYPE
    SYNTAX      DellStatusRedundancy
    ACCESS      read-only
    STATUS      mandatory
    DESCRIPTION
"0200.0010.0001.0039 This attribute defines the combined redundancy status
of all redundant memory units of this chassis."
    ::= { systemStateTableEntry 39 }
systemStateRedundantMemoryUnitStatusDetails     OBJECT-TYPE
    SYNTAX      OCTET STRING (SIZE(1..128))
    ACCESS      read-only
    STATUS      mandatory
    DESCRIPTION
"0200.0010.0001.0040 This attribute lists the redundancy status of each
redundant memory unit of this chassis.  The results are returned as a binary
octet string where each byte of the octet string represents the redundancy
status of a redundant memory unit.  The first byte returned represents the
redundancy status of the first redundant memory unit, etc.  The bytes have
the same definition type as DellStatusRedundancy."
    ::= { systemStateTableEntry 40 }
systemStateEventLogStatus                       OBJECT-TYPE
    SYNTAX      DellStatus
    ACCESS      read-only
    STATUS      mandatory
    DESCRIPTION
"0200.0010.0001.0041 This attribute defines the overall status of the
(ESM) event log of this chassis."
    ::= { systemStateTableEntry 41 }
systemStatePowerUnitStatusCombined              OBJECT-TYPE
    SYNTAX      DellStatus
    ACCESS      read-only
    STATUS      mandatory
    DESCRIPTION
"0200.0010.0001.0042 This attribute defines the combined status
of all power units of this chassis."
    ::= { systemStateTableEntry 42 }
systemStatePowerUnitStatusList                  OBJECT-TYPE
    SYNTAX      OCTET STRING (SIZE(1..128))
    ACCESS      read-only
    STATUS      mandatory
    DESCRIPTION
"0200.0010.0001.0043 This attribute lists the status of each
power unit of this chassis.  The results are returned as a binary octet
string where each byte of the octet string represents the status
of a power unit.  The first byte returned represents the status
of the first power unit, etc.  The bytes have the same definition type
as DellStatus."
    ::= { systemStateTableEntry 43 }
systemStateCoolingUnitStatusCombined            OBJECT-TYPE
    SYNTAX      DellStatus
    ACCESS      read-only
    STATUS      mandatory
    DESCRIPTION
"0200.0010.0001.0044 This attribute defines the combined status
of all cooling units of this chassis."
    ::= { systemStateTableEntry 44 }
systemStateCoolingUnitStatusList                OBJECT-TYPE
    SYNTAX      OCTET STRING (SIZE(1..128))
    ACCESS      read-only
    STATUS      mandatory
    DESCRIPTION
"0200.0010.0001.0045 This attribute lists the status of each
cooling unit of this chassis.  The results are returned as a binary octet
string where each byte of the octet string represents the status
of a cooling unit.  The first byte returned represents the status
of the first cooling unit, etc.  The bytes have the same definition type
as DellStatus."
    ::= { systemStateTableEntry 45 }
systemStateACPowerSwitchStatusCombined          OBJECT-TYPE
    SYNTAX      DellStatus
    ACCESS      read-only
    STATUS      mandatory
    DESCRIPTION
"0200.0010.0001.0046 This attribute defines the combined status
of all AC power switches of this chassis."
    ::= { systemStateTableEntry 46 }
systemStateACPowerSwitchStatusList              OBJECT-TYPE
    SYNTAX      OCTET STRING (SIZE(1..128))
    ACCESS      read-only
    STATUS      mandatory
    DESCRIPTION
"0200.0010.0001.0047 This attribute lists the status of each
AC power switch of this chassis.  The results are returned as a binary octet
string where each byte of the octet string represents the status
of an AC power switch.  The first byte returned represents the status
of the first AC power switch, etc.  The bytes have the same definition type
as DellStatus."
    ::= { systemStateTableEntry 47 }
systemStateRedundantMemoryUnitStatusCombined    OBJECT-TYPE
    SYNTAX      DellStatus
    ACCESS      read-only
    STATUS      mandatory
    DESCRIPTION
"0200.0010.0001.0048 This attribute defines the combined status
of all redundant memory units of this chassis."
    ::= { systemStateTableEntry 48 }
systemStateRedundantMemoryUnitStatusList        OBJECT-TYPE
    SYNTAX      OCTET STRING (SIZE(1..128))
    ACCESS      read-only
    STATUS      mandatory
    DESCRIPTION
"0200.0010.0001.0049 This attribute lists the status of each
redundant memory unit of this chassis.  The results are returned as a binary
octet string where each byte of the octet string represents the status
of a redundant memory unit.  The first byte returned represents the status
of the first redundant memory unit, etc.  The bytes have the same definition
type as DellStatus."
    ::= { systemStateTableEntry 49 }
systemStateProcessorDeviceStatusCombined        OBJECT-TYPE
    SYNTAX      DellStatus
    ACCESS      read-only
    STATUS      mandatory
    DESCRIPTION
"0200.0010.0001.0050 This attribute defines the combined status of all
processor devices of this chassis."
    ::= { systemStateTableEntry 50 }
systemStateProcessorDeviceStatusList            OBJECT-TYPE
    SYNTAX      OCTET STRING (SIZE(1..128))
    ACCESS      read-only
    STATUS      mandatory
    DESCRIPTION
"0200.0010.0001.0051 This attribute lists the status of each processor device
of this chassis.  The results are returned as a binary octet string where
each byte of the octet string represents the status of a processor device.
The first byte returned represents the status of the first processor device,
etc.  The bytes have the same definition type as DellStatus."
    ::= { systemStateTableEntry 51 }
systemStateBatteryStatusCombined                OBJECT-TYPE
    SYNTAX      DellStatus
    ACCESS      read-only
    STATUS      mandatory
    DESCRIPTION
"0200.0010.0001.0052 This attribute defines the combined status of all
batteries of this chassis."
    ::= { systemStateTableEntry 52 }
systemStateBatteryStatusList                    OBJECT-TYPE
    SYNTAX      OCTET STRING (SIZE(1..128))
    ACCESS      read-only
    STATUS      mandatory
    DESCRIPTION
"0200.0010.0001.0053 This attribute lists the status of each battery
of this chassis.  The results are returned as a binary octet string where
each byte of the octet string represents the status of a battery.
The first byte returned represents the status of the first battery,
etc.  The bytes have the same definition type as DellStatus."
    ::= { systemStateTableEntry 53 }
systemStateSDCardUnitStatusCombined             OBJECT-TYPE
    SYNTAX      DellStatus
    ACCESS      read-only
    STATUS      mandatory
    DESCRIPTION
"0200.0010.0001.0054 This attribute defines the combined status
of all SD Card units of this chassis."
    ::= { systemStateTableEntry 54 }
systemStateSDCardUnitStatusList                 OBJECT-TYPE
    SYNTAX      OCTET STRING (SIZE(1..128))
    ACCESS      read-only
    STATUS      mandatory
    DESCRIPTION
"0200.0010.0001.0055 This attribute lists the status of each
SD Card unit of this chassis.  The results are returned as a binary
octet string where each byte of the octet string represents the status
of a SD Card unit.  The first byte returned represents the status
of the first SD Card unit, etc.  The bytes have the same definition
type as DellStatus."
    ::= { systemStateTableEntry 55 }
systemStateSDCardDeviceStatusCombined           OBJECT-TYPE
    SYNTAX      DellStatus
    ACCESS      read-only
    STATUS      mandatory
    DESCRIPTION
"0200.0010.0001.0056 This attribute defines the combined status of all
SD Card devices of this chassis."
    ::= { systemStateTableEntry 56 }
systemStateSDCardDeviceStatusList               OBJECT-TYPE
    SYNTAX      OCTET STRING (SIZE(1..128))
    ACCESS      read-only
    STATUS      mandatory
    DESCRIPTION
"0200.0010.0001.0057 This attribute lists the status of each SD Card device
of this chassis.  The results are returned as a binary octet string where
each byte of the octet string represents the status of a SD Card device.
The first byte returned represents the status of the first SD Card device,
etc.  The bytes have the same definition type as DellStatus."
    ::= { systemStateTableEntry 57 }


-------------------------------------------------------------------------------
-- Chassis Information Group
--
-- OID Format: 1.3.6.1.4.1.674.10892.1.300
-------------------------------------------------------------------------------


DellStateCapabilitiesLogUnique                  ::= INTEGER {
    -- Note: These values are bit masks, so combination values are possible.
    unknown(1),                                 -- log state capabilities are unknown
    onlineCapable(2),                           -- log can be enabled (online) or disabled (offline)
    notReadyCapable(4),                         -- log can be not ready
    resetCapable(8)                             -- log can be reset
}
DellStateSettingsLogUnique                      ::= INTEGER {
    -- Note: These values are bit masks, so combination values are possible.
    unknown(1),                                 -- log state settings are unknown
    online(2),                                  -- log is enabled (online)
    notReady(4),                                -- log is not ready
    reset(8)                                    -- reset log
}
DellLogFormat                                   ::= INTEGER {
    raw(1),                                     -- format is Raw
    ascii(2),                                   -- format is ASCII
    uniCode(3)                                  -- format is Unicode
}


-------------------------------------------------------------------------------
-- Chassis Information Table
--
-- OID Format: 1.3.6.1.4.1.674.10892.1.300.10.1.<a>.<i1>
-------------------------------------------------------------------------------

DellChassisType                                 ::= INTEGER {
    other(1),                                   -- type is other than following values
    unknown(2),                                 -- type is unknown
    desktop(3),                                 -- type is Desktop
    lowProfileDesktop(4),                       -- type is Low Profile Desktop
    pizzaBox(5),                                -- type is Pizza Box
    miniTower(6),                               -- type is MiniTower
    tower(7),                                   -- type is Tower
    portable(8),                                -- type is Portable
    lapTop(9),                                  -- type is Laptop
    noteBook(10),                               -- type is Notebook
    handHeld(11),                               -- type is Handheld
    dockingStation(12),                         -- type is Docking Station
    allInOne(13),                               -- type is All-In-One
    subNoteBook(14),                            -- type is SubNotebook
    spaceSaving(15),                            -- type is Spacesaver
    lunchBox(16),                               -- type is Lunchbox
    mainSystemChassis(17),                      -- type is Main System Chassis
    expansionChassis(18),                       -- type is Expansion Chassis
    subChassis(19),                             -- type is SubChassis
    busExpansionChassis(20),                    -- type is Bus Expansion Chassis
    peripheralChassis(21),                      -- type is Peripheral Chassis
    raidChassis(22),                            -- type is RAID Chassis
    rackMountChassis(23),                       -- type is Rack-mounted Chassis
    sealedCasePC(24),                           -- type is Sealed-case PC
    multiSystemChassis(25)                      -- type is Multi-system Chassis
}
DellChassisSystemClass                          ::= INTEGER {
    other(1),                                   -- class is other than following values
    unknown(2),                                 -- class is unknown
    workstationClass(3),                        -- class is Workstation
    serverClass(4),                             -- class is Server
    desktopClass(5),                            -- class is Desktop
    portableClass(6),                           -- class is Portable
    netPCClass(7),                              -- class is Net PC
    storageClass(8)                             -- class is Storage
}
DellConnectionStatus                            ::= INTEGER {
    unknown(2),                                 -- status is unknown
    ok(3),                                      -- status is OK
    failure(4)                                  -- status is Failure
}
DellFanControlCapabilities                      ::= INTEGER {
    -- If 0 (zero), there are no Fan Control capabilities
    unknown(1),                                 -- fan control capabilities are unknown
    lowSpeedCapable(2),                         -- fan can be set to low speed
    highSpeedCapable(4),                        -- fan can be set to high speed
    lowOrHighSpeedCapable(6)                    -- fan can be set to low or high speed
}
DellFanControlSettings                          ::= INTEGER {
    -- If 0 (zero), there are no Fan Control settings
    unknown(1),                                 -- fan control settings are unknown
    lowSpeed(2),                                -- fan set to low speed
    highSpeed(4)                                -- fan set to high speed
}
DellLEDControlCapabilities                      ::= INTEGER {
    -- If 0 (zero), there are no LED Control capabilities
    unknown(1),                                 -- LED control capabilities are unknown
    alertOnErrorCapable(2),                     -- LED can alert on error condition
    alertOnWarningAndErrorCapable(4),           -- LED can alert on error and warning condition
    alertOnWarningOrErrorCapable(6)             -- LED can alert on error or warning condition
}
DellLEDControlSettings                          ::= INTEGER {
    -- If 0 (zero), there are no LED Control settings
    unknown(1),                                 -- LED control settings are unknown
    alertOnError(2),                            -- LED set to alert on error condition
    alertOnWarningAndError(4)                   -- LED set to alert on error or warning condition
}
DellHDFaultLEDControlCapabilities               ::= INTEGER {
    -- If 0 (zero), there are no Hard Drive Fault LED Control capabilities
    unknownCapabilities(1),                     -- LED control capabilities are unknown
    enableCapable(2),                           -- LED can be be enabled (online) or disabled (offline)
    notReadyCapable(4),                         -- LED can be not ready
    resetCapable(8)                             -- LED can be reset
}
DellHDFaultLEDControlSettings                   ::= INTEGER {
    -- If 0 (zero), there are no Hard Drive Fault LED Control settings
    unknown(1),                                 -- LED control settings are unknown
    enabled(2),                                 -- LED is enabled (online)
    notReady(4),                                -- LED is not ready
    reset(8),                                   -- reset LED
    resetAndEnable(10)                          -- reset and enable LED
}
DellChassisIdentifyControlCapabilities          ::= INTEGER {
    -- If 0 (zero), there are no Chassis Identify Control capabilities
    unknownCapabilities(1),                     -- chassis identify capabilities are unknown
    -- The objects capabilities allow it to be set to:
    enableCapable(2),                           -- chassis identify can be enabled (online) or disabled (offline)
    notReadyCapable(4),                         -- chassis identify can be not ready
    identifyCapable(8)                          -- chassis idenfity can be made to identify chassis
}
DellChassisIdentifyControlSettings              ::= INTEGER {
    -- If 0 (zero), there are no Chassis Identify Control settings
    unknown(1),                                 -- chassis identify settings are unknown
    enabled(2),                                 -- chassis identify is enabled (online)
    notReady(4),                                -- chassis identify is not ready
    identifyChassis(8),                         -- identify chassis
    identifyChassisAndEnable(10)                -- identify chassis and enabled
}
DellHostControlCapabilities                     ::= INTEGER {
    -- If 0 (zero), there are no Host Control capabilities
    manualRebootCapable(1),                     -- host can be rebooted
    manualPowerOFFCapable(2),                   -- host can be powered off
    manualPowerCycleCapable(4),                 -- host can be power cycled
    manualAllExceptOperatingSystemShutdownCapable(7),  -- all host control capabilities except OS shutdown
    manualOperatingSystemShutdownCapable(8),    -- operating system can be shutdown
    manualFullyCapable(15),                     -- all host control capabilities
    manualRebootWithOSShutdownCapable(16),      -- host can be rebooted with operating system shutdown
    manualRebootWithoutOSShutdownCapable(32),   -- host can be rebooted without operating system shutdown
    manualPowerOffWithOSShutdownCapable(64),    -- host can be powered off with operating system shutdown
    manualPowerOffWithoutOSShutdownCapable(128),-- host can be powered off without operating system shutdown
    manualPowerCycleWithOSShutdownCapable(256), -- host can be power cycled with operating system shutdown
    manualPowerCycleWithoutOSShutdownCapable(512)  -- host can be power cycled with operating system shutdown
}
DellHostControlSettings                         ::= INTEGER {
    -- If 0 (zero), there are no Host Control settings
    manualReboot(1),                            -- reboot host
    manualPowerOFF(2),                          -- power off host
    manualPowerCycle(4),                        -- power cycle host
    manualOperatingSystemShutdown(8),           -- shutdown operating system on host
    manualOperatingSystemShutdownThenReboot(9), -- shutdown operating system on host then reboot host
    manualOperatingSystemShutdownThenPowerOFF(10),   -- shutdown operating system on host then power off host
    manualOperatingSystemShutdownThenPowerCycle(12)  -- shutdown operating system on host then power cycle host
}
DellWatchDogControlCapabilities                 ::= INTEGER {
    -- If 0 (zero), there are no Watchdog Control capabilities
    automaticRebootCapable(1),                  -- watchdog can reboot host
    automaticPowerCycleCapable(2),              -- watchdog can power cycle host
    automaticNotificationCapable(4),            -- watchdog can notify
    automaticWatchDogTimerCapable(8),           -- watchdog supports timer
    automaticPowerOffCapable(16),               -- watchdog can power off host
    automaticAllExceptNotificationCapable(27),  -- all capabilities except notification
    automaticFullyCapable(31)                   -- all watchdog control capabilities
}
DellWatchControlSettings                        ::= INTEGER {
    -- If 0 (zero), there are no Watchdog Control settings
    automaticRebootEnabled(1),                  -- watchdog set for automatic reboot
    automaticPowerCycleEnabled(2),              -- watchdog set for automatic power cycle
    automaticNotificationEnabled(4),            -- watchdog set for automatic notification
    automaticPowerOffEnabled(8)                 -- watchdog set for automatic power off
}
DellWatchDogTimerCapabilities                   ::= INTEGER {
    -- If 0 (zero), there are no Watchdog Timer capabilities
    type1Capable(1),                            -- watchdog can time in range of 20-480 seconds
    type2Capable(2),                            -- watchdog can time in 30, 60, 120 and 480 second intervals
    type3Capable(4)                             -- watchdog can time in 60 second intervals
}
DellPowerButtonControlCapabilities              ::= INTEGER {
    -- If 0 (zero), there are no Power Button Control capabilities
    unknownCapabilities(1),                     -- power button capabilities are unknown
    enableCapable(2)                            -- power button can be enabled or disabled
}
DellPowerButtonControlSettings                  ::= INTEGER {
    -- If 0 (zero), there are no Power Button Control settings
    unknown(1),                                 -- power button settings are unknown
    enabled(2),                                 -- power button is enabled
    disabled(4)                                 -- power button disabled
}
DellNMIButtonControlCapabilities                ::= INTEGER {
    -- If 0 (zero), there are no NMI Button Control capabilities
    unknownCapabilities(1),                     -- NMI button capabilities are unknown
    enableCapable(2)                            -- NMI button can be enabled or disabled
}
DellNMIButtonControlSettings                    ::= INTEGER {
    -- If 0 (zero), there are no NMI Button Control settings
    unknown(1),                                 -- NMI button settings are unknown
    enabled(2),                                 -- NMI button is enabled
    disabled(4)                                 -- NMI button disabled
}
DellSystemProperties                            ::= INTEGER {
    -- Note: These values are bit masks, so combination values are possible.
    -- none(0),                                 -  no properties
    energySmart(1)                              -- Energy Smart system
}

ChassisInformationTableEntry                    ::= SEQUENCE {
    chassisIndexChassisInformation              DellObjectRange,
    chassisStateCapabilities                    DellStateCapabilities,
    chassisStateSettings                        DellStateSettings,
    chassisStatus                               DellStatus,
    chassisparentIndexReference                 DellObjectRange,
    chassisType                                 DellChassisType,
    chassisName                                 DellString,
    chassisManufacturerName                     DellString,
    chassisModelName                            DellString,
    chassisAssetTagName                         DisplayString (SIZE (0..10)),
    chassisServiceTagName                       DisplayString (SIZE (0..7)),
    chassisID                                   DellUnsigned8BitRange,
    chassisIDExtension                          DellUnsigned16BitRange,
    chassisSystemClass                          DellChassisSystemClass,
    chassisSystemName                           DellString,
    chassisSystemBootDateName                   DellDateName,
    chassisSystemDateName                       DellDateName,
    chassisSystemLocationName                   DellString,
    chassisSystemPrimaryUserName                DellString,
    chassisSystemUserPhoneNumberName            DellString,
    chassisConnectionStatusUnique               DellConnectionStatus,
    chassisFanControlCapabilitiesUnique         DellFanControlCapabilities,
    chassisFanControlSettingsUnique             DellFanControlSettings,
    chassisLEDControlCapabilitiesUnique         DellLEDControlCapabilities,
    chassisLEDControlSettingsUnique             DellLEDControlSettings,
    chassisHDFaultClearControlCapabilities      DellHDFaultLEDControlCapabilities,
    chassisHDFaultClearControlSettings          DellHDFaultLEDControlSettings,
    chassisIdentifyFlashControlCapabilities     DellChassisIdentifyControlCapabilities,
    chassisIdentifyFlashControlSettings         DellChassisIdentifyControlSettings,
    chassisLockPresent                          DellBoolean,
    chassishostControlCapabilitiesUnique        DellHostControlCapabilities,
    chassishostControlSettingsUnique            DellHostControlSettings,
    chassiswatchDogControlCapabilitiesUnique    DellWatchDogControlCapabilities,
    chassiswatchDogControlSettingsUnique        DellWatchControlSettings,
    chassiswatchDogControlExpiryTimeCapabilitiesUnique  DellWatchDogTimerCapabilities,
    chassiswatchDogControlExpiryTime            DellUnsigned16BitRange,
    chassisallowSETCommandsfromSNMP             DellBoolean,
    chassisPowerButtonControlCapabilitiesUnique DellPowerButtonControlCapabilities,
    chassisPowerButtonControlSettingsUnique     DellPowerButtonControlSettings,
    chassisResellerName                         DisplayString (SIZE (0..128)),
    chassisResellerContactInformationName       DisplayString (SIZE (0..128)),
    chassisResellerProductName                  DisplayString (SIZE (0..128)),
    chassisResellerSystemID                     DellUnsigned16BitRange,
    chassisNMIButtonControlCapabilitiesUnique   DellNMIButtonControlCapabilities,
    chassisNMIButtonControlSettingsUnique       DellNMIButtonControlSettings,
    chassisSystemProperties                     DellSystemProperties,
    chassisSystemRevisionNumber                 DellUnsigned8BitRange,
    chassisSystemRevisionName                   DellString,
    chassisExpressServiceCodeName               DellString
}

chassisInformationTable                         OBJECT-TYPE
    SYNTAX      SEQUENCE OF ChassisInformationTableEntry
    ACCESS      not-accessible
    STATUS      mandatory
    DESCRIPTION
"0300.0010 This object defines the Chassis Information Table."
    ::= { chassisInformationGroup 10 }
chassisInformationTableEntry                    OBJECT-TYPE
    SYNTAX      ChassisInformationTableEntry
    ACCESS      not-accessible
    STATUS      mandatory
    DESCRIPTION
"0300.0010.0001 This object defines the Chassis Information Table Entry."
    INDEX       { chassisIndexChassisInformation }
    ::= { chassisInformationTable 1 }

chassisIndexChassisInformation                  OBJECT-TYPE
    SYNTAX      DellObjectRange
    ACCESS      read-only
    STATUS      mandatory
    DESCRIPTION
"0300.0010.0001.0001 This attribute defines the index (one based) of the
chassis."
    ::= { chassisInformationTableEntry 1 }
chassisStateCapabilities                        OBJECT-TYPE
    SYNTAX      DellStateCapabilities
    ACCESS      read-only
    STATUS      mandatory
    DESCRIPTION
"0300.0010.0001.0002 This attribute defines the state capabilities of the
chassis."
    ::= { chassisInformationTableEntry 2 }
chassisStateSettings                            OBJECT-TYPE
    SYNTAX      DellStateSettings
    ACCESS      read-write
    STATUS      mandatory
    DESCRIPTION
"0300.0010.0001.0003 This attribute defines the state settings of the
chassis."
    ::= { chassisInformationTableEntry 3 }
chassisStatus                                   OBJECT-TYPE
    SYNTAX      DellStatus
    ACCESS      read-only
    STATUS      mandatory
    DESCRIPTION
"0300.0010.0001.0004 This attribute defines the status of the chassis."
    ::= { chassisInformationTableEntry 4 }
chassisparentIndexReference                     OBJECT-TYPE
    SYNTAX      DellObjectRange
    ACCESS      read-only
    STATUS      mandatory
    DESCRIPTION
"0300.0010.0001.0005 This attribute defines the index (one based) to the
parent chassis of this chassis, if any."
    ::= { chassisInformationTableEntry 5 }
chassisType                                     OBJECT-TYPE
    SYNTAX      DellChassisType
    ACCESS      read-only
    STATUS      mandatory
    DESCRIPTION
"0300.0010.0001.0006 This attribute defines the chassis type of the chassis."
    ::= { chassisInformationTableEntry 6 }
chassisName                                     OBJECT-TYPE
    SYNTAX      DellString
    ACCESS      read-write
    STATUS      mandatory
    DESCRIPTION
"0300.0010.0001.0007 This attribute defines the user-assigned name of the
chassis."
    ::= { chassisInformationTableEntry 7 }
chassisManufacturerName                         OBJECT-TYPE
    SYNTAX      DellString
    ACCESS      read-only
    STATUS      mandatory
    DESCRIPTION
"0300.0010.0001.0008 This attribute defines the name of the manufacturer
of the chassis."
    ::= { chassisInformationTableEntry 8 }
chassisModelName                                OBJECT-TYPE
    SYNTAX      DellString
    ACCESS      read-only
    STATUS      mandatory
    DESCRIPTION
"0300.0010.0001.0009 This attribute defines the system model type of the
chassis."
    ::= { chassisInformationTableEntry 9 }
chassisAssetTagName                             OBJECT-TYPE
    SYNTAX      DisplayString (SIZE (0..10))
    ACCESS      read-write
    STATUS      mandatory
    DESCRIPTION
"0300.0010.0001.0010 This attribute defines the asset tag name of the
chassis."
    ::= { chassisInformationTableEntry 10 }
chassisServiceTagName                           OBJECT-TYPE
    SYNTAX      DisplayString (SIZE (0..7))
    ACCESS      read-only
    STATUS      mandatory
    DESCRIPTION
"0300.0010.0001.0011 This attribute defines the service tag name of the
chassis."
    ::= { chassisInformationTableEntry 11 }
chassisID                                       OBJECT-TYPE
    SYNTAX      DellUnsigned8BitRange
    ACCESS      read-only
    STATUS      mandatory
    DESCRIPTION
"0300.0010.0001.0012 This attribute defines the system ID.  If the value
is 254 (0xFE), the attribute chassisIDExtension provides the system ID."
    ::= { chassisInformationTableEntry 12 }
chassisIDExtension                              OBJECT-TYPE
    SYNTAX      DellUnsigned16BitRange
    ACCESS      read-only
    STATUS      mandatory
    DESCRIPTION
"0300.0010.0001.0013 This attribute defines the system ID extension."
    ::= { chassisInformationTableEntry 13 }
chassisSystemClass                              OBJECT-TYPE
    SYNTAX      DellChassisSystemClass
    ACCESS      read-only
    STATUS      mandatory
    DESCRIPTION
"0300.0010.0001.0014 This attribute defines the system class."
    ::= { chassisInformationTableEntry 14 }
chassisSystemName                               OBJECT-TYPE
    SYNTAX      DellString
    ACCESS      read-only
    STATUS      mandatory
    DESCRIPTION
"0300.0010.0001.0015 This attribute defines the host name of the system."
    ::= { chassisInformationTableEntry 15 }
chassisSystemBootDateName                       OBJECT-TYPE
    SYNTAX      DellDateName
    ACCESS      read-only
    STATUS      mandatory
    DESCRIPTION
"0300.0010.0001.0016 This attribute defines boot time of the system.
Dates are defined in the ASCII format:
      yyyyMMddhhmmss.uuuuuu+fff or yyyyMMddhhmmss.uuuuuu-fff
where yyyy is the year, MM is the month, dd is the day, hh are the hours,
mm are the minutes and ss are the seconds.
uuuuuu is the number of microseconds, and +fff or -fff is the offset from
UTC in minutes."
    ::= { chassisInformationTableEntry 16 }
chassisSystemDateName                           OBJECT-TYPE
    SYNTAX      DellDateName
    ACCESS      read-only
    STATUS      mandatory
    DESCRIPTION
"0300.0010.0001.0017 This attribute defines the current time of the system.
Dates are defined in the ASCII format:
      yyyyMMddhhmmss.uuuuuu+fff or yyyyMMddhhmmss.uuuuuu-fff
where yyyy is the year, MM is the month, dd is the day, hh are the hours,
mm are the minutes and ss are the seconds.
uuuuuu is the number of microseconds, and +fff or -fff is the offset from
UTC in minutes."
    ::= { chassisInformationTableEntry 17 }
chassisSystemLocationName                       OBJECT-TYPE
    SYNTAX      DellString
    ACCESS      read-write
    STATUS      mandatory
    DESCRIPTION
"0300.0010.0001.0018 This attribute defines the location of the system."
    ::= { chassisInformationTableEntry 18 }
chassisSystemPrimaryUserName                    OBJECT-TYPE
    SYNTAX      DellString
    ACCESS      read-write
    STATUS      mandatory
    DESCRIPTION
"0300.0010.0001.0019 This attribute defines the name of the primary user
of the system."
    ::= { chassisInformationTableEntry 19 }
chassisSystemUserPhoneNumberName                OBJECT-TYPE
    SYNTAX      DellString
    ACCESS      read-write
    STATUS      mandatory
    DESCRIPTION
"0300.0010.0001.0020 This attribute defines the phone number of the primary
user of the system."
    ::= { chassisInformationTableEntry 20 }
chassisConnectionStatusUnique                   OBJECT-TYPE
    SYNTAX      DellConnectionStatus
    ACCESS      read-only
    STATUS      mandatory
    DESCRIPTION
"0300.0010.0001.0021 This attribute defines the status of the connection
of the chassis."
    ::= { chassisInformationTableEntry 21 }
chassisFanControlCapabilitiesUnique             OBJECT-TYPE
    SYNTAX      DellFanControlCapabilities
    ACCESS      read-only
    STATUS      mandatory
    DESCRIPTION
"0300.0010.0001.0022 This attribute defines the capabilities of the
fan control hardware in the chassis."
    ::= { chassisInformationTableEntry 22 }
chassisFanControlSettingsUnique                 OBJECT-TYPE
    SYNTAX      DellFanControlSettings
    ACCESS      read-write
    STATUS      mandatory
    DESCRIPTION
"0300.0010.0001.0023 This attribute defines the reading and setting of the
fan control hardware in the chassis."
    ::= { chassisInformationTableEntry 23 }
chassisLEDControlCapabilitiesUnique             OBJECT-TYPE
    SYNTAX      DellLEDControlCapabilities
    ACCESS      read-only
    STATUS      mandatory
    DESCRIPTION
"0300.0010.0001.0024 This attribute defines the capabilities of the
LED control hardware in the chassis."
    ::= { chassisInformationTableEntry 24 }
chassisLEDControlSettingsUnique                 OBJECT-TYPE
    SYNTAX      DellLEDControlSettings
    ACCESS      read-write
    STATUS      mandatory
    DESCRIPTION
"0300.0010.0001.0025 This attribute defines the reading and setting of the
LED control hardware in the chassis."
    ::= { chassisInformationTableEntry 25 }
chassisHDFaultClearControlCapabilities          OBJECT-TYPE
    SYNTAX      DellHDFaultLEDControlCapabilities
    ACCESS      read-only
    STATUS      mandatory
    DESCRIPTION
"0300.0010.0001.0026 This attribute defines if the chassis allows reset
of the chassis hard disk drive fault LED."
    ::= { chassisInformationTableEntry 26 }
chassisHDFaultClearControlSettings              OBJECT-TYPE
    SYNTAX      DellHDFaultLEDControlSettings
    ACCESS      read-write
    STATUS      mandatory
    DESCRIPTION
"0300.0010.0001.0027 This attribute allows reset of a chassis hard disk
drive fault LED."
    ::= { chassisInformationTableEntry 27 }
chassisIdentifyFlashControlCapabilities         OBJECT-TYPE
    SYNTAX      DellChassisIdentifyControlCapabilities
    ACCESS      read-only
    STATUS      mandatory
    DESCRIPTION
"0300.0010.0001.0028 This attribute defines if the chassis allows setting
of the chassis front panel LED to flash."
    ::= { chassisInformationTableEntry 28 }
chassisIdentifyFlashControlSettings             OBJECT-TYPE
    SYNTAX      DellChassisIdentifyControlSettings
    ACCESS      read-write
    STATUS      mandatory
    DESCRIPTION
"0300.0010.0001.0029 This attribute setting causes the chassis front panel
LED to flash."
    ::= { chassisInformationTableEntry 29 }
chassisLockPresent                              OBJECT-TYPE
    SYNTAX      DellBoolean
    ACCESS      read-only
    STATUS      mandatory
    DESCRIPTION
"0300.0010.0001.0030 If true, a chassis lock is present on the chassis."
    ::= { chassisInformationTableEntry 30 }
chassishostControlCapabilitiesUnique            OBJECT-TYPE
    SYNTAX      DellHostControlCapabilities
    ACCESS      read-only
    STATUS      mandatory
    DESCRIPTION
"0300.0010.0001.031 This attribute defines the capabilities of the
host control function."
    ::= { chassisInformationTableEntry 31 }
chassishostControlSettingsUnique                OBJECT-TYPE
    SYNTAX      DellHostControlSettings
    ACCESS      read-write
    STATUS      mandatory
    DESCRIPTION
"0300.0010.0001.0032 This attribute defines the settings of the
host control function."
    ::= { chassisInformationTableEntry 32 }
chassiswatchDogControlCapabilitiesUnique        OBJECT-TYPE
    SYNTAX      DellWatchDogControlCapabilities
    ACCESS      read-only
    STATUS      mandatory
    DESCRIPTION
"0300.0010.0001.0033 This attribute defines the capabilities of the
watchdog control function."
    ::= { chassisInformationTableEntry 33 }
chassiswatchDogControlSettingsUnique            OBJECT-TYPE
    SYNTAX      DellWatchControlSettings
    ACCESS      read-write
    STATUS      mandatory
    DESCRIPTION
"0300.0010.0001.0034 This attribute defines the settings of the
watchdog control function."
    ::= { chassisInformationTableEntry 34 }
chassiswatchDogControlExpiryTimeCapabilitiesUnique   OBJECT-TYPE
    SYNTAX      DellWatchDogTimerCapabilities
    ACCESS      read-only
    STATUS      mandatory
    DESCRIPTION
"0300.0010.0001.0035 This attribute defines the capabilities of the
watchdog control expiry timer function."
    ::= { chassisInformationTableEntry 35 }
chassiswatchDogControlExpiryTime                OBJECT-TYPE
    SYNTAX      DellUnsigned16BitRange
    ACCESS      read-write
    STATUS      mandatory
    DESCRIPTION
"0300.0010.0001.0036 This attribute defines the current watchdog timer
value in seconds."
    ::= { chassisInformationTableEntry 36 }
chassisallowSETCommandsfromSNMP                 OBJECT-TYPE
    SYNTAX      DellBoolean
    ACCESS      read-only
    STATUS      mandatory
    DESCRIPTION
"0300.0010.0001.0037 This attribute defines if SNMP SET type commands
are allowed or not."
    ::= { chassisInformationTableEntry 37 }
chassisPowerButtonControlCapabilitiesUnique     OBJECT-TYPE
    SYNTAX      DellPowerButtonControlCapabilities
    ACCESS      read-only
    STATUS      mandatory
    DESCRIPTION
"0300.0010.0001.0038 This attribute defines the capabilities of the
power button control hardware in the chassis."
    ::= { chassisInformationTableEntry 38 }
chassisPowerButtonControlSettingsUnique         OBJECT-TYPE
    SYNTAX      DellPowerButtonControlSettings
    ACCESS      read-write
    STATUS      mandatory
    DESCRIPTION
"0300.0010.0001.0039 This attribute defines the reading and setting of
the power button control hardware in the chassis."
    ::= { chassisInformationTableEntry 39 }
chassisResellerName                             OBJECT-TYPE
    SYNTAX      DisplayString (SIZE (0..128))
    ACCESS      read-only
    STATUS      mandatory
    DESCRIPTION
"0300.0010.0001.0040 This attribute defines the name of the system reseller."
    ::= { chassisInformationTableEntry 40 }
chassisResellerContactInformationName           OBJECT-TYPE
    SYNTAX      DisplayString (SIZE (0..128))
    ACCESS      read-only
    STATUS      mandatory
    DESCRIPTION
"0300.0010.0001.0041 This attribute defines the contact information
for the system reseller."
    ::= { chassisInformationTableEntry 41 }
chassisResellerProductName                      OBJECT-TYPE
    SYNTAX      DisplayString (SIZE (0..128))
    ACCESS      read-only
    STATUS      mandatory
    DESCRIPTION
"0300.0010.0001.0042 This attribute defines the reseller's product name
for the system."
    ::= { chassisInformationTableEntry 42 }
chassisResellerSystemID                         OBJECT-TYPE
    SYNTAX      DellUnsigned16BitRange
    ACCESS      read-only
    STATUS      mandatory
    DESCRIPTION
"0300.0010.0001.0043 This attribute defines the reseller's system ID
for the system."
    ::= { chassisInformationTableEntry 43 }
chassisNMIButtonControlCapabilitiesUnique       OBJECT-TYPE
    SYNTAX      DellNMIButtonControlCapabilities
    ACCESS      read-only
    STATUS      mandatory
    DESCRIPTION
"0300.0010.0001.0044 This attribute defines the capabilities of the
NMI button control hardware in the chassis."
    ::= { chassisInformationTableEntry 44 }
chassisNMIButtonControlSettingsUnique           OBJECT-TYPE
    SYNTAX      DellNMIButtonControlSettings
    ACCESS      read-write
    STATUS      mandatory
    DESCRIPTION
"0300.0010.0001.0045 This attribute defines the reading and setting of
the NMI button control hardware in the chassis."
    ::= { chassisInformationTableEntry 45 }
chassisSystemProperties                         OBJECT-TYPE
    SYNTAX      DellSystemProperties
    ACCESS      read-only
    STATUS      mandatory
    DESCRIPTION
"0300.0010.0001.0046 This attribute defines the properties of the system."
    ::= { chassisInformationTableEntry 46 }
chassisSystemRevisionNumber                     OBJECT-TYPE
    SYNTAX      DellUnsigned8BitRange
    ACCESS      read-only
    STATUS      mandatory
    DESCRIPTION
"0300.0010.0001.0047 This attribute defines the revision number of the system
where zero indicates the original version of the system.  The revision number
is not available on all systems."
    ::= { chassisInformationTableEntry 47 }
chassisSystemRevisionName                       OBJECT-TYPE
    SYNTAX      DellString
    ACCESS      read-only
    STATUS      mandatory
    DESCRIPTION
"0300.0010.0001.0048 This attribute defines the revision name of the system,
if applicable."
    ::= { chassisInformationTableEntry 48 }
chassisExpressServiceCodeName                   OBJECT-TYPE
    SYNTAX      DellString
    ACCESS      read-only
    STATUS      mandatory
    DESCRIPTION
"0300.0010.0001.0049 This attribute defines the Express Service Code of the
chassis."
    ::= { chassisInformationTableEntry 49 }


-------------------------------------------------------------------------------
-- Universal Unique ID (UUID) Table
--
-- OID Format: 1.3.6.1.4.1.674.10892.1.300.20.1.<a>.<i1>.<i2>
-------------------------------------------------------------------------------

DellUUIDType                                    ::= INTEGER {
    other(1),                                   -- type is other than following values
    unknown(2),                                 -- type is unknown
    motherBoard(3),                             -- type is Motherboard
    systemBackPlane(4),                         -- type is System Backplane
    powerSupplyParallelingBoard(5),             -- type is Power Supply Paralleling Board
    peripheralBayBackPlane(6),                  -- type is Peripheral Bay Backplane
    secondaryBackPlane(7)                       -- type is Secondary Backplane
}

UUIDTableEntry                                  ::= SEQUENCE {
    uUIDchassisIndex                            DellObjectRange,
    uUIDIndex                                   DellObjectRange,
    uUIDType                                    DellUUIDType,
    uUIDValue                                   OCTET STRING (SIZE(16))
}

uUIDTable                                       OBJECT-TYPE
    SYNTAX      SEQUENCE OF UUIDTableEntry
    ACCESS      not-accessible
    STATUS      mandatory
    DESCRIPTION
"0300.0020 This object defines the Universal Unique ID (UUID) Table."
    ::= { chassisInformationGroup 20 }
uUIDTableEntry                                  OBJECT-TYPE
    SYNTAX      UUIDTableEntry
    ACCESS      not-accessible
    STATUS      mandatory
    DESCRIPTION
"0300.0020.0001 This object defines the UUID Table Entry."
    INDEX       { uUIDchassisIndex,
                  uUIDIndex }
    ::= { uUIDTable 1 }

uUIDchassisIndex                                OBJECT-TYPE
    SYNTAX      DellObjectRange
    ACCESS      read-only
    STATUS      mandatory
    DESCRIPTION
"0300.0020.0001.0001 This attribute defines the index (one based) of the
associated chassis."
    ::= { uUIDTableEntry 1 }
uUIDIndex                                       OBJECT-TYPE
    SYNTAX      DellObjectRange
    ACCESS      read-only
    STATUS      mandatory
    DESCRIPTION
"0300.0020.0001.0002 This attribute defines the index (one based) of the UUID."
    ::= { uUIDTableEntry 2 }
uUIDType                                        OBJECT-TYPE
    SYNTAX      DellUUIDType
    ACCESS      read-only
    STATUS      mandatory
    DESCRIPTION
"0300.0020.0001.0003 This attribute defines the type of the UUID."
    ::= { uUIDTableEntry 3 }
uUIDValue                                       OBJECT-TYPE
    SYNTAX      OCTET STRING (SIZE(16))
    ACCESS      read-only
    STATUS      mandatory
    DESCRIPTION
"0300.0020.0001.0004 This attribute defines the value of the UUID."
    ::= { uUIDTableEntry 4 }


-------------------------------------------------------------------------------
-- Power On Self Test (POST) Log Table
--
-- OID Format: 1.3.6.1.4.1.674.10892.1.300.30.1.<a>.<i1>.<i2>
-------------------------------------------------------------------------------

PostLogTableEntry                               ::= SEQUENCE {
    postLogchassisIndex                         DellObjectRange,
    postLogRecordIndex                          DellUnsigned32BitRange,
    postLogStateCapabilitiesUnique              DellStateCapabilitiesLogUnique,
    postLogStateSettingsUnique                  DellStateSettingsLogUnique,
    postLogRecord                               DisplayString (SIZE (0..1024)),
    postLogFormat                               DellLogFormat
}

postLogTable                                    OBJECT-TYPE
    SYNTAX      SEQUENCE OF PostLogTableEntry
    ACCESS      not-accessible
    STATUS      mandatory
    DESCRIPTION
"0300.0030 This object defines the Power On Self Test (POST) Log Table."
    ::= { chassisInformationGroup 30 }
postLogTableEntry                               OBJECT-TYPE
    SYNTAX      PostLogTableEntry
    ACCESS      not-accessible
    STATUS      mandatory
    DESCRIPTION
"0300.0030.0001 This object defines the POST Log Table Entry."
    INDEX       { postLogchassisIndex,
                  postLogRecordIndex }
    ::= { postLogTable 1 }

postLogchassisIndex                             OBJECT-TYPE
    SYNTAX      DellObjectRange
    ACCESS      read-only
    STATUS      mandatory
    DESCRIPTION
"0300.0030.0001.0001 This attribute defines the index (one based) of the
associated chassis."
    ::= { postLogTableEntry 1 }
postLogRecordIndex                              OBJECT-TYPE
    SYNTAX      DellUnsigned32BitRange
    ACCESS      read-only
    STATUS      mandatory
    DESCRIPTION
"0300.0030.0001.0002 This attribute defines the index (one based) of the
POST log record."
    ::= { postLogTableEntry 2 }
postLogStateCapabilitiesUnique                  OBJECT-TYPE
    SYNTAX      DellStateCapabilitiesLogUnique
    ACCESS      read-only
    STATUS      mandatory
    DESCRIPTION
"0300.0030.0001.0003 This attribute defines the state capabilities of the
object that is writing the POST log."
    ::= { postLogTableEntry 3 }
postLogStateSettingsUnique                      OBJECT-TYPE
    SYNTAX      DellStateSettingsLogUnique
    ACCESS      read-write
    STATUS      mandatory
    DESCRIPTION
"0300.0030.0001.0004 This attribute defines the state settings of the
object that is writing the POST log."
    ::= { postLogTableEntry 4 }
postLogRecord                                   OBJECT-TYPE
    SYNTAX       DisplayString (SIZE (0..1024))
    ACCESS      read-only
    STATUS      mandatory
    DESCRIPTION
"0300.0030.0001.0005 This attribute defines the data of the POST log record."
    ::= { postLogTableEntry 5 }
postLogFormat                                   OBJECT-TYPE
    SYNTAX      DellLogFormat
    ACCESS      read-only
    STATUS      mandatory
    DESCRIPTION
"0300.0030.0001.0006 This attribute defines the format of the POST log record."
    ::= { postLogTableEntry 6 }


-------------------------------------------------------------------------------
-- Event (ESM) Log Table
--
-- OID Format: 1.3.6.1.4.1.674.10892.1.300.40.1.<a>.<i1>.<i2>
-------------------------------------------------------------------------------

EventLogTableEntry                              ::= SEQUENCE {
    eventLogchassisIndex                        DellObjectRange,
    eventLogRecordIndex                         DellUnsigned32BitRange,
    eventLogStateCapabilitiesUnique             DellStateCapabilitiesLogUnique,
    eventLogStateSettingsUnique                 DellStateSettingsLogUnique,
    eventLogRecord                              DisplayString (SIZE (0..1024)),
    eventLogFormat                              DellLogFormat,
    eventLogSeverityStatus                      DellStatus,
    eventLogDateName                            DellDateName
}

eventLogTable                                   OBJECT-TYPE
    SYNTAX      SEQUENCE OF EventLogTableEntry
    ACCESS      not-accessible
    STATUS      mandatory
    DESCRIPTION
"0300.0040 This object defines the Event (ESM) Log Table."
    ::= { chassisInformationGroup 40 }
eventLogTableEntry                              OBJECT-TYPE
    SYNTAX      EventLogTableEntry
    ACCESS      not-accessible
    STATUS      mandatory
    DESCRIPTION
"0300.0040.0001 This object defines the Event (ESM) Log Table Entry."
    INDEX       { eventLogchassisIndex,
                  eventLogRecordIndex }
    ::= { eventLogTable 1 }

eventLogchassisIndex                            OBJECT-TYPE
    SYNTAX      DellObjectRange
    ACCESS      read-only
    STATUS      mandatory
    DESCRIPTION
"0300.0040.0001.0001 This attribute defines the index (one based) of the
associated chassis."
    ::= { eventLogTableEntry 1 }
eventLogRecordIndex                             OBJECT-TYPE
    SYNTAX      DellUnsigned32BitRange
    ACCESS      read-only
    STATUS      mandatory
    DESCRIPTION
"0300.0040.0001.0002 This attribute defines the index (one based) of the
event log record."
    ::= { eventLogTableEntry 2 }
eventLogStateCapabilitiesUnique                 OBJECT-TYPE
    SYNTAX      DellStateCapabilitiesLogUnique
    ACCESS      read-only
    STATUS      mandatory
    DESCRIPTION
"0300.0040.0001.0003 This attribute defines the state capabilities of the
object that is writing the event log."
    ::= { eventLogTableEntry 3 }
eventLogStateSettingsUnique                     OBJECT-TYPE
    SYNTAX      DellStateSettingsLogUnique
    ACCESS      read-write
    STATUS      mandatory
    DESCRIPTION
"0300.0040.0001.0004 This attribute defines the state settings of the
object that is writing the event log."
    ::= { eventLogTableEntry 4 }
eventLogRecord                                  OBJECT-TYPE
    SYNTAX       DisplayString (SIZE (0..1024))
    ACCESS      read-only
    STATUS      mandatory
    DESCRIPTION
"0300.0040.0001.0005 This attribute defines the data of the event log record."
    ::= { eventLogTableEntry 5 }
eventLogFormat                                  OBJECT-TYPE
    SYNTAX      DellLogFormat
    ACCESS      read-only
    STATUS      mandatory
    DESCRIPTION
"0300.0040.0001.0006 This attribute defines the format of the event log record."
    ::= { eventLogTableEntry 6 }
eventLogSeverityStatus                          OBJECT-TYPE
    SYNTAX      DellStatus
    ACCESS      read-only
    STATUS      mandatory
    DESCRIPTION
"0300.0040.0001.0007 This attribute defines the severity of the
event log record."
    ::= { eventLogTableEntry 7 }
eventLogDateName                                OBJECT-TYPE
    SYNTAX      DellDateName
    ACCESS      read-only
    STATUS      mandatory
    DESCRIPTION
"0300.0040.0001.0008 This attribute defines the date and time of the
event log record."
    ::= { eventLogTableEntry 8 }


-------------------------------------------------------------------------------
-- System BIOS Table
--
-- OID Format: 1.3.6.1.4.1.674.10892.1.300.50.1.<a>.<i1>.<i2>
-------------------------------------------------------------------------------

SystemBIOSTableEntry                            ::= SEQUENCE {
    systemBIOSchassisIndex                      DellObjectRange,
    systemBIOSIndex                             DellObjectRange,
    systemBIOSStateCapabilities                 DellStateCapabilities,
    systemBIOSStateSettings                     DellStateSettings,
    systemBIOSStatus                            DellStatus,
    systemBIOSSize                              DellUnsigned32BitRange,
    systemBIOSReleaseDateName                   DellDateName,
    systemBIOSVersionName                       DellString,
    systemBIOSStartingAddress                   DellUnsigned64BitRange,
    systemBIOSEndingAddress                     DellUnsigned64BitRange,
    systemBIOSManufacturerName                  DellString,
    systemBIOSCharacteristics                   DellUnsigned64BitRange,
    systemBIOSCharacteristicsExt1               DellUnsigned8BitRange,
    systemBIOSCharacteristicsExt2               DellUnsigned8BitRange
}

systemBIOSTable                                 OBJECT-TYPE
    SYNTAX      SEQUENCE OF SystemBIOSTableEntry
    ACCESS      not-accessible
    STATUS      mandatory
    DESCRIPTION
"0300.0050 This object defines the System BIOS Table."
    ::= { chassisInformationGroup 50 }
systemBIOSTableEntry                            OBJECT-TYPE
    SYNTAX      SystemBIOSTableEntry
    ACCESS      not-accessible
    STATUS      mandatory
    DESCRIPTION
"0300.0050.0001 This object defines the System BIOS Table Entry."
    INDEX       { systemBIOSchassisIndex,
                  systemBIOSIndex }
    ::= { systemBIOSTable 1 }

systemBIOSchassisIndex                          OBJECT-TYPE
    SYNTAX      DellObjectRange
    ACCESS      read-only
    STATUS      mandatory
    DESCRIPTION
"0300.0050.0001.0001 This attribute defines the index (one based) of the
associated chassis."
    ::= { systemBIOSTableEntry 1 }
systemBIOSIndex                                 OBJECT-TYPE
    SYNTAX      DellObjectRange
    ACCESS      read-only
    STATUS      mandatory
    DESCRIPTION
"0300.0050.0001.0002 This attribute defines the index (one based) of the
system BIOS."
    ::= { systemBIOSTableEntry 2 }
systemBIOSStateCapabilities                     OBJECT-TYPE
    SYNTAX      DellStateCapabilities
    ACCESS      read-only
    STATUS      mandatory
    DESCRIPTION
"0300.0050.0001.0003 This attribute defines the state capabilities of the
system BIOS."
    ::= { systemBIOSTableEntry 3 }
systemBIOSStateSettings                         OBJECT-TYPE
    SYNTAX      DellStateSettings
    ACCESS      read-write
    STATUS      mandatory
    DESCRIPTION
"0300.0050.0001.0004 This attribute defines the state settings of the
system BIOS."
    ::= { systemBIOSTableEntry 4 }
systemBIOSStatus                                OBJECT-TYPE
    SYNTAX      DellStatus
    ACCESS      read-only
    STATUS      mandatory
    DESCRIPTION
"0300.0050.0001.0005 This attribute defines the status of the system BIOS."
    ::= { systemBIOSTableEntry 5 }
systemBIOSSize                                  OBJECT-TYPE
    SYNTAX      DellUnsigned32BitRange
    ACCESS      read-only
    STATUS      mandatory
    DESCRIPTION
"0300.0050.0001.0006 This attribute defines the image size of the
system BIOS in KBytes.  Zero indicates size is unknown."
    ::= { systemBIOSTableEntry 6 }
systemBIOSReleaseDateName                       OBJECT-TYPE
    SYNTAX      DellDateName
    ACCESS      read-only
    STATUS      mandatory
    DESCRIPTION
"0300.0050.0001.0007 This attribute defines the release date name of the
system BIOS."
    ::= { systemBIOSTableEntry 7 }
systemBIOSVersionName                           OBJECT-TYPE
    SYNTAX      DellString
    ACCESS      read-only
    STATUS      mandatory
    DESCRIPTION
"0300.0050.0001.0008 This attribute defines the version name of the
system BIOS."
    ::= { systemBIOSTableEntry 8 }
systemBIOSStartingAddress                       OBJECT-TYPE
    SYNTAX      DellUnsigned64BitRange
    ACCESS      read-only
    STATUS      mandatory
    DESCRIPTION
"0300.0050.0001.0009 This attribute defines the starting address of the
system BIOS.  Zero indicates the starting address is unknown."
    ::= { systemBIOSTableEntry 9 }
systemBIOSEndingAddress                         OBJECT-TYPE
    SYNTAX      DellUnsigned64BitRange
    ACCESS      read-only
    STATUS      mandatory
    DESCRIPTION
"0300.0050.0001.0010 This attribute defines the ending address of the
system BIOS.  Zero indicates the starting address is unknown."
    ::= { systemBIOSTableEntry 10 }
systemBIOSManufacturerName                      OBJECT-TYPE
    SYNTAX      DellString
    ACCESS      read-only
    STATUS      mandatory
    DESCRIPTION
"0300.0050.0001.0011 This attribute defines the name of the manufacturer
of the system BIOS."
    ::= { systemBIOSTableEntry 11 }
systemBIOSCharacteristics                       OBJECT-TYPE
    SYNTAX      DellUnsigned64BitRange
    ACCESS      read-only
    STATUS      mandatory
    DESCRIPTION
"0300.0050.0001.0012 This attribute defines characteristics of the
system BIOS.  This attribute is a bit field where a bit has the meaning
defined below when set to 1 (one).  Bit 63 is the first bit in the value,
and bit 0 is the last bit in the value.  See the description of
DellUnsigned64BitRange at the beginning of this file for more information
on the format of the value.

NOTE: Bits 48-63 need to be examined in the context of the system ID.
The system ID is available in the attribute chassisID.  If the value
for chassisID is non-zero, bits 48-63 have the meaning defined below.

    Bit
    Position    Meaning if Set
    --------    --------------
    Bit 0       Reserved
    Bit 1       Reserved
    Bit 2       Unknown
    Bit 3       BIOS Characteristics Not Supported
    Bit 4       ISA is supported
    Bit 5       MCA is supported
    Bit 6       EISA is supported
    Bit 7       PCI is supported
    Bit 8       PC Card (PCMCIA) is supported
    Bit 9       Plug and Play is supported
    Bit 10      APM is supported
    Bit 11      BIOS is Upgradeable (Flash)
    Bit 12      BIOS shadowing is allowed
    Bit 13      VL-VESA is supported
    Bit 14      ESCD support is available
    Bit 15      Boot from CD is supported
    Bit 16      Selectable Boot is supported
    Bit 17      BIOS ROM is socketed
    Bit 18      Boot From PC Card (PCMCIA) is supported
    Bit 19      EDD (Enhanced Disk Drive) Specification is supported
    Bit 20      Int 13h - Japanese Floppy for NEC 9800 1.2mb (3.5 in, 1k Bytes/Sector, 360 RPM) is supported
    Bit 21      Int 13h - Japanese Floppy for Toshiba 1.2mb (3.5 in, 360 RPM) is supported
    Bit 22      Int 13h - 5.25 in / 360 KB Floppy Services are supported
    Bit 23      Int 13h - 5.25 in /1.2MB Floppy Services are supported
    Bit 24      Int 13h - 3.5 in / 720 KB Floppy Services are supported
    Bit 25      Int 13h - 3.5 in / 2.88 MB Floppy Services are supported
    Bit 26      Int 5h, Print Screen Service is supported
    Bit 27      Int 9h, 8042 Keyboard services are supported
    Bit 28      Int 14h, Serial Services are supported
    Bit 29      Int 17h, Printer Services are supported
    Bit 30      Int 10h, CGA/Mono Video Services are supported
    Bit 31      NEC PC-98
    Bit 32-47   Reserved
    Bit 48      Built-in NIC supports Magic Packet
    Bit 49      System supports Wake-on-LAN
    Bit 50      System supports chassis intrusion
    Bit 51      Built-in NIC supports pattern-matching
    Bit 52      System BIOS supports a 7-character service tag
    Bit 53-63   Reserved"
    ::= { systemBIOSTableEntry 12 }
systemBIOSCharacteristicsExt1                   OBJECT-TYPE
    SYNTAX      DellUnsigned8BitRange
    ACCESS      read-only
    STATUS      mandatory
    DESCRIPTION
"0300.0050.0001.0013 This attribute defines additional characteristics of the
system BIOS.  This attribute is a bit field where a bit has the meaning
defined below when set to 1 (one).

    Bit
    Position    Meaning if Set
    --------    --------------
    Bit 0       ACPI supported
    Bit 1       USB Legacy is supported
    Bit 2       AGP is supported
    Bit 3       I2O boot is supported
    Bit 4       LS-120 boot is supported
    Bit 5       ATAPI ZIP Drive boot is supported
    Bit 6       1394 boot is supported
    Bit 7       Smart Battery supported"
    ::= { systemBIOSTableEntry 13 }
systemBIOSCharacteristicsExt2                   OBJECT-TYPE
    SYNTAX      DellUnsigned8BitRange
    ACCESS      read-only
    STATUS      mandatory
    DESCRIPTION
"0300.0050.0001.0014 This attribute defines additional characteristics of the
system BIOS.  This attribute is a bit field where a bit has the meaning
defined below when set to 1 (one).

    Bit
    Position    Meaning if Set
    --------    --------------
    Bit 0       BIOS Boot Specification supported
    Bit 1       Function key-initiated Network Service boot supported
    Bit 2       Targeted Content Distribution supported
    Bit 3-7     Reserved"
    ::= { systemBIOSTableEntry 14 }


-------------------------------------------------------------------------------
-- Firmware Table
--
-- OID Format: 1.3.6.1.4.1.674.10892.1.300.60.1.<a>.<i1>.<i2>
-------------------------------------------------------------------------------

DellFirmwareType                                ::= INTEGER {
    other(1),                                   -- type is other than following values
    unknown(2),                                 -- type is unknown
    systemBIOS(3),                              -- type is System BIOS
    embeddedSystemManagementController(4),      -- type is Embedded System Management Controller
    powerSupplyParallelingBoard(5),             -- type is Power Supply Paralleling Board
    systemBackPlane(6),                         -- type is System (Primary) Backplane
    powerVault2XXSKernel(7),                    -- type is PowerVault 2XXS Kernel
    powerVault2XXSApplication(8),               -- type is PowerVault 2XXS Application
    frontPanel(9),                              -- type is Front Panel Controller
    baseboardManagementController(10),          -- type is Baseboard Management Controller
    hotPlugPCI(11),                             -- type is Hot Plug PCI Controller
    sensorData(12),                             -- type is Sensor Data Records
    peripheralBay(13),                          -- type is Peripheral Bay Backplane
    secondaryBackPlane(14),                     -- type is Secondary Backplane for ESM 2 systems
    secondaryBackPlaneESM3And4(15),             -- type is Secondary Backplane for ESM 3 and 4 systems
    rac(16),                                    -- type is Remote Access Controller
    iDRAC(17),                                  -- type is Integrated Dell Remote Access Controller
    unifiedServerConfigurator(19),              -- type is Unified Server Configurator
    lifecycleController(20)                     -- type is Lifecycle Controller
}

FirmwareTableEntry                              ::= SEQUENCE {
    firmwarechassisIndex                        DellObjectRange,
    firmwareIndex                               DellObjectRange,
    firmwareStateCapabilities                   DellStateCapabilities,
    firmwareStateSettings                       DellStateSettings,
    firmwareStatus                              DellStatus,
    firmwareSize                                DellUnsigned16BitRange,
    firmwareType                                DellFirmwareType,
    firmwareTypeName                            DellString,
    firmwareUpdateCapabilities                  DellUnsigned16BitRange,
    firmwareDateName                            OCTET STRING (SIZE(8)),
    firmwareVersionName                         DellString
}

firmwareTable                                   OBJECT-TYPE
    SYNTAX      SEQUENCE OF FirmwareTableEntry
    ACCESS      not-accessible
    STATUS      mandatory
    DESCRIPTION
"0300.0060 This object defines the Firmware Table."
    ::= { chassisInformationGroup 60 }
firmwareTableEntry                              OBJECT-TYPE
    SYNTAX      FirmwareTableEntry
    ACCESS      not-accessible
    STATUS      mandatory
    DESCRIPTION
"0300.0060.0001 This object defines the Firmware Table Entry."
    INDEX       { firmwarechassisIndex,
                  firmwareIndex }
    ::= { firmwareTable 1 }

firmwarechassisIndex                            OBJECT-TYPE
    SYNTAX      DellObjectRange
    ACCESS      read-only
    STATUS      mandatory
    DESCRIPTION
"0300.0060.0001.0001 This attribute defines the index (one based) of the
associated chassis."
    ::= { firmwareTableEntry 1 }
firmwareIndex                                   OBJECT-TYPE
    SYNTAX      DellObjectRange
    ACCESS      read-only
    STATUS      mandatory
    DESCRIPTION
"0300.0060.0001.0002 This attribute defines the index (one based) of the
firmware."
    ::= { firmwareTableEntry 2 }
firmwareStateCapabilities                       OBJECT-TYPE
    SYNTAX      DellStateCapabilities
    ACCESS      read-only
    STATUS      mandatory
    DESCRIPTION
"0300.0060.0001.0003 This attribute defines the state capabilities of the
firmware."
    ::= { firmwareTableEntry 3 }
firmwareStateSettings                           OBJECT-TYPE
    SYNTAX      DellStateSettings
    ACCESS      read-write
    STATUS      mandatory
    DESCRIPTION
"0300.0060.0001.0004 This attribute defines the state settings of the
firmware."
    ::= { firmwareTableEntry 4 }
firmwareStatus                                  OBJECT-TYPE
    SYNTAX      DellStatus
    ACCESS      read-only
    STATUS      mandatory
    DESCRIPTION
"0300.0060.0001.0005 This attribute defines the status of the firmware."
    ::= { firmwareTableEntry 5 }
firmwareSize                                    OBJECT-TYPE
    SYNTAX      DellUnsigned16BitRange
    ACCESS      read-only
    STATUS      mandatory
    DESCRIPTION
"0300.0060.0001.0006 This attribute defines the image size of the firmware
in KBytes.  Zero indicates size is unknown."
    ::= { firmwareTableEntry 6 }
firmwareType                                    OBJECT-TYPE
    SYNTAX      DellFirmwareType
    ACCESS      read-only
    STATUS      mandatory
    DESCRIPTION
"0300.0060.0001.0007 This attribute defines the type of firmware."
    ::= { firmwareTableEntry 7 }
firmwareTypeName                                OBJECT-TYPE
    SYNTAX      DellString
    ACCESS      read-only
    STATUS      mandatory
    DESCRIPTION
"0300.0060.0001.0008 This attribute defines the type name of the firmware."
    ::= { firmwareTableEntry 8 }
firmwareUpdateCapabilities                      OBJECT-TYPE
    SYNTAX      DellUnsigned16BitRange
    ACCESS      read-only
    STATUS      mandatory
    DESCRIPTION
"0300.0060.0001.0009 This attribute defines the bitmap of supported methods
for firmware update."
    ::= { firmwareTableEntry 9 }
firmwareDateName                                OBJECT-TYPE
    SYNTAX      OCTET STRING (SIZE(8))
    ACCESS      read-only
    STATUS      mandatory
    DESCRIPTION
"0300.0060.0001.0010 This attribute defines the release date of the firmware."
    ::= { firmwareTableEntry 10 }
firmwareVersionName                             OBJECT-TYPE
    SYNTAX      DellString
    ACCESS      read-only
    STATUS      mandatory
    DESCRIPTION
"0300.0060.0001.0011 This attribute defines the version of the firmware."
    ::= { firmwareTableEntry 11 }


-------------------------------------------------------------------------------
-- Intrusion Table
--
-- OID Format: 1.3.6.1.4.1.674.10892.1.300.70.1.<a>.<i1>.<i2>
-------------------------------------------------------------------------------

DellIntrusionReading                            ::= INTEGER {
    chassisNotBreached(1),                      -- chassis not breached and no uncleared breaches
    chassisBreached(2),                         -- chassis currently breached
    chassisBreachedPrior(3),                    -- chassis breached prior to boot and has not been cleared
    chassisBreachSensorFailure(4)               -- intrusion sensor has failed
}
DellIntrusionType                               ::= INTEGER {
    chassisBreachDetectionWhenPowerON(1),       -- type is detect intrusion while power on
    chassisBreachDetectionWhenPowerOFF(2)       -- type is detect intrusion while power off
}

IntrusionTableEntry                             ::= SEQUENCE {
    intrusionchassisIndex                       DellObjectRange,
    intrusionIndex                              DellObjectRange,
    intrusionStateCapabilities                  DellStateCapabilities,
    intrusionStateSettings                      DellStateSettings,
    intrusionStatus                             DellStatus,
    intrusionReading                            DellIntrusionReading,
    intrusionType                               DellIntrusionType,
    intrusionLocationName                       DellString
}

intrusionTable                                  OBJECT-TYPE
    SYNTAX      SEQUENCE OF IntrusionTableEntry
    ACCESS      not-accessible
    STATUS      mandatory
    DESCRIPTION
"0300.0070 This object defines the Intrusion Table."
    ::= { chassisInformationGroup 70 }
intrusionTableEntry                             OBJECT-TYPE
    SYNTAX      IntrusionTableEntry
    ACCESS      not-accessible
    STATUS      mandatory
    DESCRIPTION
"0300.0070.0001 This object defines the Intrusion Table Entry."
    INDEX       { intrusionchassisIndex,
                  intrusionIndex }
    ::= { intrusionTable 1 }

intrusionchassisIndex                           OBJECT-TYPE
    SYNTAX      DellObjectRange
    ACCESS      read-only
    STATUS      mandatory
    DESCRIPTION
"0300.0070.0001.0001 This attribute defines the index (one based) of the
associated chassis."
    ::= { intrusionTableEntry 1 }
intrusionIndex                                  OBJECT-TYPE
    SYNTAX      DellObjectRange
    ACCESS      read-only
    STATUS      mandatory
    DESCRIPTION
"0300.0070.0001.0002 This attribute defines the index (one based) of the
intrusion sensor."
    ::= { intrusionTableEntry 2 }
intrusionStateCapabilities                      OBJECT-TYPE
    SYNTAX      DellStateCapabilities
    ACCESS      read-only
    STATUS      mandatory
    DESCRIPTION
"0300.0070.0001.0003 This attribute defines the state capabilities of the
intrusion sensor."
    ::= { intrusionTableEntry 3 }
intrusionStateSettings                          OBJECT-TYPE
    SYNTAX      DellStateSettings
    ACCESS      read-write
    STATUS      mandatory
    DESCRIPTION
"0300.0070.0001.0004 This attribute defines the state settings of the
intrusion sensor."
    ::= { intrusionTableEntry 4 }
intrusionStatus                                 OBJECT-TYPE
    SYNTAX      DellStatus
    ACCESS      read-only
    STATUS      mandatory
    DESCRIPTION
"0300.0070.0001.0005 This attribute defines the status of the
intrusion sensor."
    ::= { intrusionTableEntry 5 }
intrusionReading                                OBJECT-TYPE
    SYNTAX      DellIntrusionReading
    ACCESS      read-only
    STATUS      mandatory
    DESCRIPTION
"0300.0070.0001.0006 This attribute defines the reading of the
intrusion sensor."
    ::= { intrusionTableEntry 6 }
intrusionType                                   OBJECT-TYPE
    SYNTAX      DellIntrusionType
    ACCESS      read-only
    STATUS      mandatory
    DESCRIPTION
"0300.0070.0001.0007 This attribute defines the type of the
intrusion sensor."
    ::= { intrusionTableEntry 7 }
intrusionLocationName                           OBJECT-TYPE
    SYNTAX      DellString
    ACCESS      read-only
    STATUS      mandatory
    DESCRIPTION
"0300.0070.0001.0008 This attribute defines the location of the
intrusion sensor."
    ::= { intrusionTableEntry 8 }


-------------------------------------------------------------------------------
-- Base Board Table
--
-- OID Format: 1.3.6.1.4.1.674.10892.1.300.80.1.<a>.<i1>.<i2>
-------------------------------------------------------------------------------

DellBaseBoardType                               ::= INTEGER {
    unknown(1),                                 -- type is unknown
    other(2),                                   -- type is other than following values
    serverBlade(3),                             -- type is Server Blade
    connectivitySwitch(4),                      -- type is Connectivity Switch
    systemManagementModule(5),                  -- type is System Management Module
    processorModule(6),                         -- type is Processor Module
    ioModule(7),                                -- type is I/O Module
    memoryModule(8),                            -- type is Memory Module
    daughterBoard(9),                           -- type is Daughter Board
    motherboard(10),                            -- type is Motherboard
    processorMemoryModule(11),                  -- type is Processor/Memory Module
    processorIOModule(12),                      -- type is Processor/IO Module
    interconnectBoard(13)                       -- type is Interconnect Board
}
DellBaseBoardFeatureFlags                       ::= INTEGER {
    -- Note: These values are bit fields, so combination values are possible.
    -- If 0 (zero), base board has none of the following features:
    boardIsHostingBoard(1),                     -- board is Hosting Board
    boardRequiresDaughterBoard(2),              -- board requires at least one Daughter Board or Auxiliary Card
    boardIsRemovable(4),                        -- board is Removable
    boardIsReplaceable(8),                      -- board is Replaceable
    boardIsHotSwappable(16)                     -- board is Hot Swappable
}

BaseBoardTableEntry                             ::= SEQUENCE {
    baseBoardChassisIndex                       DellObjectRange,
    baseBoardIndex                              DellObjectRange,
    baseBoardStateCapabilities                  DellStateCapabilities,
    baseBoardStateSettings                      DellStateSettings,
    baseBoardStatus                             DellStatus,
    baseBoardFeatureFlags                       DellBaseBoardFeatureFlags,
    baseBoardType                               DellBaseBoardType,
    baseBoardTypeName                           DellString,
    baseBoardLocationName                       DellString,
    baseBoardManufacturerName                   DellString,
    baseBoardProductName                        DellString,
    baseBoardVersionName                        DellString,
    baseBoardServiceTagName                     DellString,
    baseBoardPiecePartIDName                    DellString,
    baseBoardAssetTagName                       DellString,
    baseBoardExpressServiceCodeName             DellString
}

baseBoardTable                                  OBJECT-TYPE
    SYNTAX      SEQUENCE OF BaseBoardTableEntry
    ACCESS      not-accessible
    STATUS      mandatory
    DESCRIPTION
"0300.0080 This object defines the Base Board Table."
    ::= { chassisInformationGroup 80 }
baseBoardTableEntry                             OBJECT-TYPE
    SYNTAX      BaseBoardTableEntry
    ACCESS      not-accessible
    STATUS      mandatory
    DESCRIPTION
"0300.0080.0001 This object defines the Base Board Table Entry."
    INDEX       { baseBoardChassisIndex,
                  baseBoardIndex }
    ::= { baseBoardTable 1 }

baseBoardChassisIndex                           OBJECT-TYPE
    SYNTAX      DellObjectRange
    ACCESS      read-only
    STATUS      mandatory
    DESCRIPTION
"0300.0080.0001.0001 This attribute defines the index (one based) of the
associated chassis."
    ::= { baseBoardTableEntry 1 }
baseBoardIndex                                  OBJECT-TYPE
    SYNTAX      DellObjectRange
    ACCESS      read-only
    STATUS      mandatory
    DESCRIPTION
"0300.0080.0001.0002 This attribute defines the index (one based) of the
base board."
    ::= { baseBoardTableEntry 2 }
baseBoardStateCapabilities                      OBJECT-TYPE
    SYNTAX      DellStateCapabilities
    ACCESS      read-only
    STATUS      mandatory
    DESCRIPTION
"0300.0080.0001.0003 This attribute defines the state capabilities of the
base board."
    ::= { baseBoardTableEntry 3 }
baseBoardStateSettings                          OBJECT-TYPE
    SYNTAX      DellStateSettings
    ACCESS      read-write
    STATUS      mandatory
    DESCRIPTION
"0300.0080.0001.0004 This attribute defines the state settings of the
base board."
    ::= { baseBoardTableEntry 4 }
baseBoardStatus                                 OBJECT-TYPE
    SYNTAX      DellStatus
    ACCESS      read-only
    STATUS      mandatory
    DESCRIPTION
"0300.0080.0001.0005 This attribute defines the status of the base board."
    ::= { baseBoardTableEntry 5 }
baseBoardFeatureFlags                           OBJECT-TYPE
    SYNTAX      DellBaseBoardFeatureFlags
    ACCESS      read-only
    STATUS      mandatory
    DESCRIPTION
"0300.0080.0001.0006 This attribute defines the features of the base board."
    ::= { baseBoardTableEntry 6 }
baseBoardType                                   OBJECT-TYPE
    SYNTAX      DellBaseBoardType
    ACCESS      read-only
    STATUS      mandatory
    DESCRIPTION
"0300.0080.0001.0007 This attribute defines the type of the base board."
    ::= { baseBoardTableEntry 7 }
baseBoardTypeName                               OBJECT-TYPE
    SYNTAX      DellString
    ACCESS      read-only
    STATUS      mandatory
    DESCRIPTION
"0300.0080.0001.0008 This attribute defines the type name of the base board."
    ::= { baseBoardTableEntry 8 }
baseBoardLocationName                           OBJECT-TYPE
    SYNTAX      DellString
    ACCESS      read-only
    STATUS      mandatory
    DESCRIPTION
"0300.0080.0001.0009 This attribute defines the location of the base board."
    ::= { baseBoardTableEntry 9 }
baseBoardManufacturerName                       OBJECT-TYPE
    SYNTAX      DellString
    ACCESS      read-only
    STATUS      mandatory
    DESCRIPTION
"0300.0080.0001.0010 This attribute defines the name of the manufacturer
of the base board."
    ::= { baseBoardTableEntry 10 }
baseBoardProductName                            OBJECT-TYPE
    SYNTAX      DellString
    ACCESS      read-only
    STATUS      mandatory
    DESCRIPTION
"0300.0080.0001.0011 This attribute defines the product name of the
base board."
    ::= { baseBoardTableEntry 11 }
baseBoardVersionName                            OBJECT-TYPE
    SYNTAX      DellString
    ACCESS      read-only
    STATUS      mandatory
    DESCRIPTION
"0300.0080.0001.0012 This attribute defines the version of the base board."
    ::= { baseBoardTableEntry 12 }
baseBoardServiceTagName                         OBJECT-TYPE
    SYNTAX      DellString
    ACCESS      read-only
    STATUS      mandatory
    DESCRIPTION
"0300.0080.0001.0013 This attribute defines the service tag of the base board."
    ::= { baseBoardTableEntry 13 }
baseBoardPiecePartIDName                        OBJECT-TYPE
    SYNTAX      DellString
    ACCESS      read-only
    STATUS      mandatory
    DESCRIPTION
"0300.0080.0001.0014 This attribute defines the Piece Part ID (PPID) of the
base board."
    ::= { baseBoardTableEntry 14 }
baseBoardAssetTagName                           OBJECT-TYPE
    SYNTAX      DellString
    ACCESS      read-only
    STATUS      mandatory
    DESCRIPTION
"0300.0080.0001.0015 This attribute defines the asset tag of the base board."
    ::= { baseBoardTableEntry 15 }
baseBoardExpressServiceCodeName                 OBJECT-TYPE
    SYNTAX      DellString
    ACCESS      read-only
    STATUS      mandatory
    DESCRIPTION
"0300.0080.0001.0016 This attribute defines the Express Service Code of the
base board."
    ::= { baseBoardTableEntry 16 }


-------------------------------------------------------------------------------
-- Operating System Group
--
-- OID Format: 1.3.6.1.4.1.674.10892.1.400
-------------------------------------------------------------------------------


-------------------------------------------------------------------------------
-- Operating System Table
--
-- OID Format: 1.3.6.1.4.1.674.10892.1.400.10.1.<a>.<i1>
-------------------------------------------------------------------------------

OperatingSystemTableEntry                       ::= SEQUENCE {
    operatingSystemchassisIndex                 DellObjectRange,
    operatingSystemStateCapabilities            DellStateCapabilities,
    operatingSystemStateSettings                DellStateSettings,
    operatingSystemStatus                       DellStatus,
    operatingSystemIsPrimary                    DellBoolean,
    operatingSystemOperatingSystemName          DisplayString (SIZE (0..255)),
    operatingSystemOperatingSystemVersionName   DisplayString (SIZE (0..255))
}

operatingSystemTable                            OBJECT-TYPE
    SYNTAX      SEQUENCE OF OperatingSystemTableEntry
    ACCESS      not-accessible
    STATUS      mandatory
    DESCRIPTION
"0400.0010 This object defines the Operating System Table."
    ::= { operatingSystemGroup 10 }
operatingSystemTableEntry                       OBJECT-TYPE
    SYNTAX      OperatingSystemTableEntry
    ACCESS      not-accessible
    STATUS      mandatory
    DESCRIPTION
"0400.0010.0001 This object defines the Operating System Table Entry."
    INDEX       { operatingSystemchassisIndex }
    ::= { operatingSystemTable 1 }

operatingSystemchassisIndex                     OBJECT-TYPE
    SYNTAX      DellObjectRange
    ACCESS      read-only
    STATUS      mandatory
    DESCRIPTION
"0400.0010.0001.0001 This attribute defines the index (one based) of the
associated chassis."
    ::= { operatingSystemTableEntry 1 }
operatingSystemStateCapabilities                OBJECT-TYPE
    SYNTAX      DellStateCapabilities
    ACCESS      read-only
    STATUS      mandatory
    DESCRIPTION
"0400.0010.0001.0002 This attribute defines the state capabilities of the
operating system."
    ::= { operatingSystemTableEntry 2 }
operatingSystemStateSettings                    OBJECT-TYPE
    SYNTAX      DellStateSettings
    ACCESS      read-write
    STATUS      mandatory
    DESCRIPTION
"0400.0010.0001.0003 This attribute defines the state settings of the
operating system."
    ::= { operatingSystemTableEntry 3 }
operatingSystemStatus                           OBJECT-TYPE
    SYNTAX      DellStatus
    ACCESS      read-only
    STATUS      mandatory
    DESCRIPTION
"0400.0010.0001.0004 This attribute defines the status of the
operating system."
    ::= { operatingSystemTableEntry 4 }
operatingSystemIsPrimary                        OBJECT-TYPE
    SYNTAX      DellBoolean
    ACCESS      read-only
    STATUS      mandatory
    DESCRIPTION
"0400.0010.0001.0005 This attribute defines if this operating system is the
primary operating system or not."
    ::= { operatingSystemTableEntry 5 }
operatingSystemOperatingSystemName              OBJECT-TYPE
    SYNTAX      DisplayString (SIZE (0..255))
    ACCESS      read-only
    STATUS      mandatory
    DESCRIPTION
"0400.0010.0001.0006 This attribute defines the name of the operating system."
    ::= { operatingSystemTableEntry 6 }
operatingSystemOperatingSystemVersionName       OBJECT-TYPE
    SYNTAX      DisplayString (SIZE (0..255))
    ACCESS      read-only
    STATUS      mandatory
    DESCRIPTION
"0400.0010.0001.0007 This attribute defines the version of the operating system."
    ::= { operatingSystemTableEntry 7 }


-------------------------------------------------------------------------------
-- Operating System Memory Table
--
-- OID Format: 1.3.6.1.4.1.674.10892.1.400.20.1.<a>.<i1>
-------------------------------------------------------------------------------

OperatingSystemMemoryTableEntry                 ::= SEQUENCE {
    operatingSystemMemorychassisIndex           DellObjectRange,
    operatingSystemMemoryStateCapabilities      DellStateCapabilities,
    operatingSystemMemoryStateSettings          DellStateSettings,
    operatingSystemMemoryStatus                 DellStatus,
    operatingSystemMemoryTotalPhysicalSize      DellUnsigned32BitRange,
    operatingSystemMemoryAvailablePhysicalSize  DellUnsigned32BitRange,
    operatingSystemMemoryTotalPageFileSize      DellUnsigned32BitRange,
    operatingSystemMemoryAvailablePageFileSize  DellUnsigned32BitRange,
    operatingSystemMemoryTotalVirtualSize       DellUnsigned32BitRange,
    operatingSystemMemoryAvailableVirtualSize   DellUnsigned32BitRange
}

operatingSystemMemoryTable                      OBJECT-TYPE
    SYNTAX      SEQUENCE OF OperatingSystemMemoryTableEntry
    ACCESS      not-accessible
    STATUS      mandatory
    DESCRIPTION
"0400.0020 This object defines the Operating System Memory Table."
    ::= { operatingSystemGroup 20 }
operatingSystemMemoryTableEntry                 OBJECT-TYPE
    SYNTAX      OperatingSystemMemoryTableEntry
    ACCESS      not-accessible
    STATUS      mandatory
    DESCRIPTION
"0400.0020.0001 This object defines the Operating System Memory Table Entry."
    INDEX       { operatingSystemMemorychassisIndex }
    ::= { operatingSystemMemoryTable 1 }

operatingSystemMemorychassisIndex               OBJECT-TYPE
    SYNTAX      DellObjectRange
    ACCESS      read-only
    STATUS      mandatory
    DESCRIPTION
"0400.0020.0001.0001 This attribute defines the index (one based) of the
associated chassis."
    ::= { operatingSystemMemoryTableEntry 1 }
operatingSystemMemoryStateCapabilities          OBJECT-TYPE
    SYNTAX      DellStateCapabilities
    ACCESS      read-only
    STATUS      mandatory
    DESCRIPTION
"0400.0020.0001.0002 This attribute defines the state capabilities of the
operating system memory."
    ::= { operatingSystemMemoryTableEntry 2 }
operatingSystemMemoryStateSettings              OBJECT-TYPE
    SYNTAX      DellStateSettings
    ACCESS      read-write
    STATUS      mandatory
    DESCRIPTION
"0400.0020.0001.0003 This attribute defines the state settings of the
operating system memory."
    ::= { operatingSystemMemoryTableEntry 3 }
operatingSystemMemoryStatus                     OBJECT-TYPE
    SYNTAX      DellStatus
    ACCESS      read-only
    STATUS      mandatory
    DESCRIPTION
"0400.0020.0001.0004 This attribute defines the status of the
operating system memory."
    ::= { operatingSystemMemoryTableEntry 4 }
operatingSystemMemoryTotalPhysicalSize          OBJECT-TYPE
    SYNTAX      DellUnsigned32BitRange
    ACCESS      read-only
    STATUS      mandatory
    DESCRIPTION
"0400.0020.0001.0005 This attribute defines the total physical memory
for the operating system memory in KBytes."
    ::= { operatingSystemMemoryTableEntry 5 }
operatingSystemMemoryAvailablePhysicalSize      OBJECT-TYPE
    SYNTAX      DellUnsigned32BitRange
    ACCESS      read-only
    STATUS      mandatory
    DESCRIPTION
"0400.0020.0001.0006 This attribute defines the available physical memory
for the operating system memory in KBytes."
    ::= { operatingSystemMemoryTableEntry 6 }
operatingSystemMemoryTotalPageFileSize          OBJECT-TYPE
    SYNTAX      DellUnsigned32BitRange
    ACCESS      read-only
    STATUS      mandatory
    DESCRIPTION
"0400.0020.0001.0007 This attribute defines the total page file memory
for the operating system memory in KBytes."
    ::= { operatingSystemMemoryTableEntry 7 }
operatingSystemMemoryAvailablePageFileSize      OBJECT-TYPE
    SYNTAX      DellUnsigned32BitRange
    ACCESS      read-only
    STATUS      mandatory
    DESCRIPTION
"0400.0020.0001.0008 This attribute defines the available page file memory
for the operating system memory in KBytes."
    ::= { operatingSystemMemoryTableEntry 8 }
operatingSystemMemoryTotalVirtualSize           OBJECT-TYPE
    SYNTAX      DellUnsigned32BitRange
    ACCESS      read-only
    STATUS      mandatory
    DESCRIPTION
"0400.0020.0001.0009 This attribute defines the total virtual memory
for the operating system memory in KBytes."
    ::= { operatingSystemMemoryTableEntry 9 }
operatingSystemMemoryAvailableVirtualSize       OBJECT-TYPE
    SYNTAX      DellUnsigned32BitRange
    ACCESS      read-only
    STATUS      mandatory
    DESCRIPTION
"0400.0020.0001.0010 This attribute defines the available virtual memory
for the operating system memory in KBytes."
    ::= { operatingSystemMemoryTableEntry 10 }


-------------------------------------------------------------------------------
-- System Resource Group
--
-- OID Format: 1.3.6.1.4.1.674.10892.1.500
-------------------------------------------------------------------------------


-------------------------------------------------------------------------------
-- System Resource Map Table
--
-- OID Format: 1.3.6.1.4.1.674.10892.1.500.10.1.<a>.<i1>.<i2>
-------------------------------------------------------------------------------

DellSystemResourceMapType                       ::= INTEGER {
    other(1),                                   -- type is other than following values
    unknown(2),                                 -- type is unknown
    typeOne(3)                                  -- type is type 1 (one)
}

SystemResourceMapTableEntry                     ::= SEQUENCE {
    systemResourceMapchassisIndex               DellObjectRange,
    systemResourceMapIndex                      DellObjectRange,
    systemResourceMapStateCapabilities          DellStateCapabilities,
    systemResourceMapStateSettings              DellStateSettings,
    systemResourceMapStatus                     DellStatus,
    systemResourceMapType                       DellSystemResourceMapType
}

systemResourceMapTable                          OBJECT-TYPE
    SYNTAX      SEQUENCE OF SystemResourceMapTableEntry
    ACCESS      not-accessible
    STATUS      mandatory
    DESCRIPTION
"0500.0010 This object defines the System Resource Map Table."
    ::= { systemResourceGroup 10 }
systemResourceMapTableEntry                     OBJECT-TYPE
    SYNTAX      SystemResourceMapTableEntry
    ACCESS      not-accessible
    STATUS      mandatory
    DESCRIPTION
"0500.0010.0001 This object defines the System Resource Map Table Entry."
    INDEX       { systemResourceMapchassisIndex,
                  systemResourceMapIndex }
    ::= { systemResourceMapTable 1 }

systemResourceMapchassisIndex                   OBJECT-TYPE
    SYNTAX      DellObjectRange
    ACCESS      read-only
    STATUS      mandatory
    DESCRIPTION
"0500.0010.0001.0001 This attribute defines the index (one based) of the
associated chassis."
    ::= { systemResourceMapTableEntry 1 }
systemResourceMapIndex                          OBJECT-TYPE
    SYNTAX      DellObjectRange
    ACCESS      read-only
    STATUS      mandatory
    DESCRIPTION
"0500.0010.0001.0002 This attribute defines the index (one based) of the
system resource map."
    ::= { systemResourceMapTableEntry 2 }
systemResourceMapStateCapabilities              OBJECT-TYPE
    SYNTAX      DellStateCapabilities
    ACCESS      read-only
    STATUS      mandatory
    DESCRIPTION
"0500.0010.0001.0003 This attribute defines the state capabilities of the
system resource map."
    ::= { systemResourceMapTableEntry 3 }
systemResourceMapStateSettings                  OBJECT-TYPE
    SYNTAX      DellStateSettings
    ACCESS      read-write
    STATUS      mandatory
    DESCRIPTION
"0500.0010.0001.0004 This attribute defines the state settings of the
system resource map."
    ::= { systemResourceMapTableEntry 4 }
systemResourceMapStatus                         OBJECT-TYPE
    SYNTAX      DellStatus
    ACCESS      read-only
    STATUS      mandatory
    DESCRIPTION
"0500.0010.0001.0005 This attribute defines the status of the
system resource map."
    ::= { systemResourceMapTableEntry 5 }
systemResourceMapType                           OBJECT-TYPE
    SYNTAX      DellSystemResourceMapType
    ACCESS      read-only
    STATUS      mandatory
    DESCRIPTION
"0500.0010.0001.0006 This attribute defines the type of the system resource map."
    ::= { systemResourceMapTableEntry 6 }


-------------------------------------------------------------------------------
-- System Resource Owner Table
--
-- OID Format: 1.3.6.1.4.1.674.10892.1.500.20.1.<a>.<i1>.<i2>
-------------------------------------------------------------------------------

DellResourceOwnerInterfaceType                  ::= INTEGER {
    typeIsOther(1),                             -- type is other than following values
    typeIsUnknown(2),                           -- type is unknown
    typeIsInternal(3),                          -- type is Internal
    typeIsISA(4),                               -- type is ISA Bus
    typeIsEISA(5),                              -- type is EISA Bus
    typeIsMCA(6),                               -- type is MCA Bus
    typeIsTurboChannel(7),                      -- type is TurboChannel Bus
    typeIsPCI(8)                                -- type is PCI Bus
}

SystemResourceOwnerTableEntry                   ::= SEQUENCE {
    systemResourceOwnerchassisIndex             DellObjectRange,
    systemResourceOwnerIndex                    DellObjectRange,
    systemResourceOwnerStateCapabilities        DellStateCapabilities,
    systemResourceOwnerStateSettings            DellStateSettings,
    systemResourceOwnerStatus                   DellStatus,
    systemResourceOwnerInterfaceType            DellResourceOwnerInterfaceType,
    systemResourceMapIndexReference             DellObjectRange,
    systemResourceOwnerDescriptionName          DellString,
    systemResourceOwnerInterfaceInstance        DellObjectRange
}

systemResourceOwnerTable                        OBJECT-TYPE
    SYNTAX      SEQUENCE OF SystemResourceOwnerTableEntry
    ACCESS      not-accessible
    STATUS      mandatory
    DESCRIPTION
"0500.0020 This object defines the System Resource Owner Table."
    ::= { systemResourceGroup 20 }
systemResourceOwnerTableEntry                   OBJECT-TYPE
    SYNTAX      SystemResourceOwnerTableEntry
    ACCESS      not-accessible
    STATUS      mandatory
    DESCRIPTION
"0500.0020.0001 This object defines the System Resource Owner Table Entry."
    INDEX       { systemResourceOwnerchassisIndex,
                  systemResourceOwnerIndex }
    ::= { systemResourceOwnerTable 1 }

systemResourceOwnerchassisIndex                 OBJECT-TYPE
    SYNTAX      DellObjectRange
    ACCESS      read-only
    STATUS      mandatory
    DESCRIPTION
"0500.0020.0001.0001 This attribute defines the index (one based) of the
associated chassis."
    ::= { systemResourceOwnerTableEntry 1 }
systemResourceOwnerIndex                        OBJECT-TYPE
    SYNTAX      DellObjectRange
    ACCESS      read-only
    STATUS      mandatory
    DESCRIPTION
"0500.0020.0001.0002 This attribute defines the index of (one based) of the
system resource owner."
    ::= { systemResourceOwnerTableEntry 2 }
systemResourceOwnerStateCapabilities            OBJECT-TYPE
    SYNTAX      DellStateCapabilities
    ACCESS      read-only
    STATUS      mandatory
    DESCRIPTION
"0500.0020.0001.0003 This attribute defines the state capabilities of the
system resource owner."
    ::= { systemResourceOwnerTableEntry 3 }
systemResourceOwnerStateSettings                OBJECT-TYPE
    SYNTAX      DellStateSettings
    ACCESS      read-write
    STATUS      mandatory
    DESCRIPTION
"0500.0020.0001.0004 This attribute defines the state settings of the
system resource owner."
    ::= { systemResourceOwnerTableEntry 4 }
systemResourceOwnerStatus                       OBJECT-TYPE
    SYNTAX      DellStatus
    ACCESS      read-only
    STATUS      mandatory
    DESCRIPTION
"0500.0020.0001.0005 This attribute defines the status of the
system resource owner."
    ::= { systemResourceOwnerTableEntry 5 }
systemResourceOwnerInterfaceType                OBJECT-TYPE
    SYNTAX      DellResourceOwnerInterfaceType
    ACCESS      read-only
    STATUS      mandatory
    DESCRIPTION
"0500.0020.0001.0006 This attribute defines the interface type of the
system resource owner."
    ::= { systemResourceOwnerTableEntry 6 }
systemResourceMapIndexReference                 OBJECT-TYPE
    SYNTAX      DellObjectRange
    ACCESS      read-only
    STATUS      mandatory
    DESCRIPTION
"0500.0020.0001.0007 This attribute defines the index to the associated
system resource map."
    ::= { systemResourceOwnerTableEntry 7 }
systemResourceOwnerDescriptionName              OBJECT-TYPE
    SYNTAX      DellString
    ACCESS      read-only
    STATUS      mandatory
    DESCRIPTION
"0500.0020.0001.0008 This attribute defines the description of the
system resource owner."
    ::= { systemResourceOwnerTableEntry 8 }
systemResourceOwnerInterfaceInstance            OBJECT-TYPE
    SYNTAX      DellObjectRange
    ACCESS      read-only
    STATUS      mandatory
    DESCRIPTION
"0500.0020.0001.0009 This attribute defines the index to the associated
system resource owner interface type."
    ::= { systemResourceOwnerTableEntry 9 }


-------------------------------------------------------------------------------
-- System Resource I/O Port Table
--
-- OID Format: 1.3.6.1.4.1.674.10892.1.500.30.1.<a>.<i1>.<i2>
-------------------------------------------------------------------------------

DellResourceShareDisposition                    ::= INTEGER {
    shareIsOther(1),                            -- disposition is other than following values
    shareIsUnknown(2),                          -- disposition is unknown
    shareIsDeviceExclusive(3),                  -- disposition is Device Exclusive
    shareIsDriverExclusive(4),                  -- disposition is Driver Exclusive
    shareIsShared(5)                            -- disposition is Shared
}

SystemResourceIOPortTableEntry                  ::= SEQUENCE {
    systemResourceIOPortchassisIndex            DellObjectRange,
    systemResourceIOPortIndex                   DellObjectRange,
    systemResourceIOPortStateCapabilities       DellStateCapabilities,
    systemResourceIOPortStateSettings           DellStateSettings,
    systemResourceIOPortStatus                  DellStatus,
    systemResourceIOPortOwnerIndexReference     DellObjectRange,
    systemResourceIOPortShareDisposition        DellResourceShareDisposition,
    systemResourceIOPortStartingAddress         DellUnsigned64BitRange,
    systemResourceIOPortEndingAddress           DellUnsigned64BitRange
}

systemResourceIOPortTable                       OBJECT-TYPE
    SYNTAX      SEQUENCE OF SystemResourceIOPortTableEntry
    ACCESS      not-accessible
    STATUS      mandatory
    DESCRIPTION
"0500.0030 This object defines the System Resource I/O Port Table."
    ::= { systemResourceGroup 30 }
systemResourceIOPortTableEntry                  OBJECT-TYPE
    SYNTAX      SystemResourceIOPortTableEntry
    ACCESS      not-accessible
    STATUS      mandatory
    DESCRIPTION
"0500.0030.0001 This object defines the System Resource I/O Port Table Entry."
    INDEX       { systemResourceIOPortchassisIndex,
                  systemResourceIOPortIndex }
    ::= { systemResourceIOPortTable 1 }

systemResourceIOPortchassisIndex            OBJECT-TYPE
    SYNTAX      DellObjectRange
    ACCESS      read-only
    STATUS      mandatory
    DESCRIPTION
"0500.0030.0001.0001 This attribute defines the index (one based) of the
associated chassis."
    ::= { systemResourceIOPortTableEntry 1 }
systemResourceIOPortIndex                       OBJECT-TYPE
    SYNTAX      DellObjectRange
    ACCESS      read-only
    STATUS      mandatory
    DESCRIPTION
"0500.0030.0001.0002 This attribute defines the index (one based) of the
system resource I/O port."
    ::= { systemResourceIOPortTableEntry 2 }
systemResourceIOPortStateCapabilities           OBJECT-TYPE
    SYNTAX      DellStateCapabilities
    ACCESS      read-only
    STATUS      mandatory
    DESCRIPTION
"0500.0030.0001.0003 This attribute defines the state capabilities of the
system resource I/O port."
    ::= { systemResourceIOPortTableEntry 3 }
systemResourceIOPortStateSettings               OBJECT-TYPE
    SYNTAX      DellStateSettings
    ACCESS      read-write
    STATUS      mandatory
    DESCRIPTION
"0500.0030.0001.0004 This attribute defines the state settings of the
system resource I/O port."
    ::= { systemResourceIOPortTableEntry 4 }
systemResourceIOPortStatus                      OBJECT-TYPE
    SYNTAX      DellStatus
    ACCESS      read-only
    STATUS      mandatory
    DESCRIPTION
"0500.0030.0001.0005 This attribute defines the status of the
system resource I/O port."
    ::= { systemResourceIOPortTableEntry 5 }
systemResourceIOPortOwnerIndexReference         OBJECT-TYPE
    SYNTAX      DellObjectRange
    ACCESS      read-only
    STATUS      mandatory
    DESCRIPTION
"0500.0030.0001.0006 This attribute defines the index to the associated
system resource owner for this system resource I/O port."
    ::= { systemResourceIOPortTableEntry 6 }
systemResourceIOPortShareDisposition            OBJECT-TYPE
    SYNTAX      DellResourceShareDisposition
    ACCESS      read-only
    STATUS      mandatory
    DESCRIPTION
"0500.0030.0001.0007 This attribute defines the share disposition of the
system resource I/O port."
    ::= { systemResourceIOPortTableEntry 7 }
systemResourceIOPortStartingAddress             OBJECT-TYPE
    SYNTAX      DellUnsigned64BitRange
    ACCESS      read-only
    STATUS      mandatory
    DESCRIPTION
"0500.0030.0001.0008 This attribute defines the 64-bit starting address
of the system resource I/O port."
    ::= { systemResourceIOPortTableEntry 8 }
systemResourceIOPortEndingAddress              OBJECT-TYPE
    SYNTAX      DellUnsigned64BitRange
    ACCESS      read-only
    STATUS      mandatory
    DESCRIPTION
"0500.0030.0001.0009 This attribute defines the 64-bit ending address
of the system resource I/O port."
    ::= { systemResourceIOPortTableEntry 9 }


-------------------------------------------------------------------------------
-- System Resource Memory Table
--
-- OID Format: 1.3.6.1.4.1.674.10892.1.500.40.1.<a>.<i1>.<i2>
-------------------------------------------------------------------------------

DellResourceMemoryFlags                         ::= INTEGER {
    memoryIsReadOnly(1),                        -- memory is read-only
    memoryIsWriteOnly(2),                       -- memory is write-only
    memoryIsReadAndWrite(3),                    -- memory is read-write
    memoryIsPreFetchable(4),                    -- memory is prefetchable
    memoryIsCombinedWritable(8),                -- memory is combined writable
    memoryIsF24(16)                             -- memory is F24
}

SystemResourceMemoryTableEntry                  ::= SEQUENCE {
    systemResourceMemorychassisIndex            DellObjectRange,
    systemResourceMemoryIndex                   DellObjectRange,
    systemResourceMemoryStateCapabilities       DellStateCapabilities,
    systemResourceMemoryStateSettings           DellStateSettings,
    systemResourceMemoryStatus                  DellStatus,
    systemResourceMemoryOwnerIndexReference     DellObjectRange,
    systemResourceMemoryShareDisposition        DellResourceShareDisposition,
    systemResourceMemoryStartingAddress         DellUnsigned64BitRange,
    systemResourceMemoryEndingAddress           DellUnsigned64BitRange,
    systemResourceMemoryFlags                   DellResourceMemoryFlags
}

systemResourceMemoryTable                       OBJECT-TYPE
    SYNTAX      SEQUENCE OF SystemResourceMemoryTableEntry
    ACCESS      not-accessible
    STATUS      mandatory
    DESCRIPTION
"0500.0040 This object defines the System Resource Memory Table."
    ::= { systemResourceGroup 40 }
systemResourceMemoryTableEntry                  OBJECT-TYPE
    SYNTAX      SystemResourceMemoryTableEntry
    ACCESS      not-accessible
    STATUS      mandatory
    DESCRIPTION
"0500.0040.0001 This object defines the System Resource Memory Table Entry."
    INDEX       { systemResourceMemorychassisIndex,
                  systemResourceMemoryIndex }
    ::= { systemResourceMemoryTable 1 }

systemResourceMemorychassisIndex                OBJECT-TYPE
    SYNTAX      DellObjectRange
    ACCESS      read-only
    STATUS      mandatory
    DESCRIPTION
"0500.0040.0001.0001 This attribute defines the index (one based) of the
associated chassis."
    ::= { systemResourceMemoryTableEntry 1 }
systemResourceMemoryIndex                       OBJECT-TYPE
    SYNTAX      DellObjectRange
    ACCESS      read-only
    STATUS      mandatory
    DESCRIPTION
"0500.0040.0001.0002 This attribute defines the index (one based) of the
system resource memory."
    ::= { systemResourceMemoryTableEntry 2 }
systemResourceMemoryStateCapabilities           OBJECT-TYPE
    SYNTAX      DellStateCapabilities
    ACCESS      read-only
    STATUS      mandatory
    DESCRIPTION
"0500.0040.0001.0003 This attribute defines the state capabilities of the
system resource memory."
    ::= { systemResourceMemoryTableEntry 3 }
systemResourceMemoryStateSettings               OBJECT-TYPE
    SYNTAX      DellStateSettings
    ACCESS      read-write
    STATUS      mandatory
    DESCRIPTION
"0500.0040.0001.0004 This attribute defines the state settings of the
system resource memory."
    ::= { systemResourceMemoryTableEntry 4 }
systemResourceMemoryStatus                      OBJECT-TYPE
    SYNTAX      DellStatus
    ACCESS      read-only
    STATUS      mandatory
    DESCRIPTION
"0500.0040.0001.0005 This attribute defines the status of the
system resource memory."
    ::= { systemResourceMemoryTableEntry 5 }
systemResourceMemoryOwnerIndexReference         OBJECT-TYPE
    SYNTAX      DellObjectRange
    ACCESS      read-only
    STATUS      mandatory
    DESCRIPTION
"0500.0040.0001.0006 This attribute defines the index to the associated
system resource owner for this system resource memory."
    ::= { systemResourceMemoryTableEntry 6 }
systemResourceMemoryShareDisposition            OBJECT-TYPE
    SYNTAX      DellResourceShareDisposition
    ACCESS      read-only
    STATUS      mandatory
    DESCRIPTION
"0500.0040.0001.0007 This attribute defines the share disposition of the
system resource memory."
    ::= { systemResourceMemoryTableEntry 7 }
systemResourceMemoryStartingAddress             OBJECT-TYPE
    SYNTAX      DellUnsigned64BitRange
    ACCESS      read-only
    STATUS      mandatory
    DESCRIPTION
"0500.0040.0001.0008 This attribute defines the 64-bit starting address
of the system resource memory."
    ::= { systemResourceMemoryTableEntry 8 }
systemResourceMemoryEndingAddress               OBJECT-TYPE
    SYNTAX      DellUnsigned64BitRange
    ACCESS      read-only
    STATUS      mandatory
    DESCRIPTION
"0500.0040.0001.0009 This attribute defines the 64-bit ending address
of the system resource memory."
    ::= { systemResourceMemoryTableEntry 9 }
systemResourceMemoryFlags                       OBJECT-TYPE
    SYNTAX      DellResourceMemoryFlags
    ACCESS      read-only
    STATUS      mandatory
    DESCRIPTION
"0500.0040.0001.0010 This attribute defines the permission flags of the
system resource memory."
    ::= { systemResourceMemoryTableEntry 10 }


-------------------------------------------------------------------------------
-- System Resource Interrupts Table
--
-- OID Format: 1.3.6.1.4.1.674.10892.1.500.50.1.<a>.<i1>.<i2>
-------------------------------------------------------------------------------

DellResourceInterruptType                       ::= INTEGER {
    interruptIsLevelSensitive(1),               -- type is Level Sensitive
    interruptIsLatched(2)                       -- type is Latched
}
DellResourceInterruptTrigger                    ::= INTEGER {
    interruptIsActiveWhenLow(1),                -- trigger is active on low signal
    interruptIsActiveWhenHigh(2)                -- trigger is active on high signal
}

SystemResourceInterruptTableEntry               ::= SEQUENCE {
    systemResourceInterruptchassisIndex         DellObjectRange,
    systemResourceInterruptIndex                DellObjectRange,
    systemResourceInterruptStateCapabilities    DellStateCapabilities,
    systemResourceInterruptStateSettings        DellStateSettings,
    systemResourceInterruptStatus               DellStatus,
    systemResourceInterruptOwnerIndexReference  DellObjectRange,
    systemResourceInterruptShareDisposition     DellResourceShareDisposition,
    systemResourceInterruptLevel                DellUnsigned32BitRange,
    systemResourceInterruptType                 DellResourceInterruptType,
    systemResourceInterruptTrigger              DellResourceInterruptTrigger
}

systemResourceInterruptTable                    OBJECT-TYPE
    SYNTAX      SEQUENCE OF SystemResourceInterruptTableEntry
    ACCESS      not-accessible
    STATUS      mandatory
    DESCRIPTION
"0500.0050 This object defines the System Resource Interrupts Table."
    ::= { systemResourceGroup 50 }
systemResourceInterruptTableEntry               OBJECT-TYPE
    SYNTAX      SystemResourceInterruptTableEntry
    ACCESS      not-accessible
    STATUS      mandatory
    DESCRIPTION
"0500.0050.0001 This object defines the System Resource Interrupts Table Entry."
    INDEX       { systemResourceInterruptchassisIndex,
                  systemResourceInterruptIndex }
    ::= { systemResourceInterruptTable 1 }

systemResourceInterruptchassisIndex             OBJECT-TYPE
    SYNTAX      DellObjectRange
    ACCESS      read-only
    STATUS      mandatory
    DESCRIPTION
"0500.0050.0001.0001 This attribute defines the index (one based) of the
associated chassis."
    ::= { systemResourceInterruptTableEntry 1 }
systemResourceInterruptIndex                    OBJECT-TYPE
    SYNTAX      DellObjectRange
    ACCESS      read-only
    STATUS      mandatory
    DESCRIPTION
"0500.0050.0001.0002 This attribute defines the index (one based) of the
system resource interrupt."
    ::= { systemResourceInterruptTableEntry 2 }
systemResourceInterruptStateCapabilities        OBJECT-TYPE
    SYNTAX      DellStateCapabilities
    ACCESS      read-only
    STATUS      mandatory
    DESCRIPTION
"0500.0050.0001.0003 This attribute defines the state capabilities of the
system resource interrupt."
    ::= { systemResourceInterruptTableEntry 3 }
systemResourceInterruptStateSettings           OBJECT-TYPE
    SYNTAX      DellStateSettings
    ACCESS      read-write
    STATUS      mandatory
    DESCRIPTION
"0500.0050.0001.0004 This attribute defines the state settings of the
system resource interrupt."
    ::= { systemResourceInterruptTableEntry 4 }
systemResourceInterruptStatus                   OBJECT-TYPE
    SYNTAX      DellStatus
    ACCESS      read-only
    STATUS      mandatory
    DESCRIPTION
"0500.0050.0001.0005 This attribute defines the status of the
system resource interrupt."
    ::= { systemResourceInterruptTableEntry 5 }
systemResourceInterruptOwnerIndexReference      OBJECT-TYPE
    SYNTAX      DellObjectRange
    ACCESS      read-only
    STATUS      mandatory
    DESCRIPTION
"0500.0050.0001.0006 This attribute defines the index to the associated
system resource owner for this system resource interrupt."
    ::= { systemResourceInterruptTableEntry 6 }
systemResourceInterruptShareDisposition         OBJECT-TYPE
    SYNTAX      DellResourceShareDisposition
    ACCESS      read-only
    STATUS      mandatory
    DESCRIPTION
"0500.0050.0001.0007 This attribute defines the share disposition of the
system resource interrupt."
    ::= { systemResourceInterruptTableEntry 7 }
systemResourceInterruptLevel                    OBJECT-TYPE
    SYNTAX      DellUnsigned32BitRange
    ACCESS      read-only
    STATUS      mandatory
    DESCRIPTION
"0500.0050.0001.0008 This attribute defines the interrupt request level (IRQ)
of the system resource interrupt."
    ::= { systemResourceInterruptTableEntry 8 }
systemResourceInterruptType                     OBJECT-TYPE
    SYNTAX      DellResourceInterruptType
    ACCESS      read-only
    STATUS      mandatory
    DESCRIPTION
"0500.0050.0001.0009 This attribute defines the interrupt type of the
system resource interrupt."
    ::= { systemResourceInterruptTableEntry 9 }
systemResourceInterruptTrigger                  OBJECT-TYPE
    SYNTAX      DellResourceInterruptTrigger
    ACCESS      read-only
    STATUS      mandatory
    DESCRIPTION
"0500.0050.0001.0010 This attribute defines the interrupt trigger of the
system resource interrupt."
    ::= { systemResourceInterruptTableEntry 10 }


-------------------------------------------------------------------------------
-- System Resource DMA Table
--
-- OID Format: 1.3.6.1.4.1.674.10892.1.500.60.1.<a>.<i1>.<i2>
-------------------------------------------------------------------------------

DellResourceDMATransferWidth                    ::= INTEGER {
    dmaTransferWidthIsOther(1),                 -- width is other than following values
    dmaTransferWidthIsunknown(2),               -- width is unknown
    dmaTransferWidthIs8Bits(3),                 -- width is 8 bits
    dmaTransferWidthIs16Bits(4),                -- width is 16 bits
    dmaTransferWidthIs32Bits(5),                -- width is 32 bits
    dmaTransferWidthIs64Bits(6),                -- width is 64 bits
    dmaTransferWidthIs128Bits(7)                -- width is 128 bits
}
DellResourceDMABusMaster                        ::= INTEGER {
    dmaIsOther(1),                              -- bus master capability is other than following values
    dmaIsUnknown(2),                            -- bus master capability is unknown
    dmaIsNotABusmaster(3),                      -- DMA has no bus master capability
    dmaIsABusmaster(4)                          -- DMA has bus master capability
}

SystemResourceDMATableEntry                     ::= SEQUENCE {
    systemResourceDMAchassisIndex               DellObjectRange,
    systemResourceDMAIndex                      DellObjectRange,
    systemResourceDMAStateCapabilities          DellStateCapabilities,
    systemResourceDMAStateSettings              DellStateSettings,
    systemResourceDMAStatus                     DellStatus,
    systemResourceDMAOwnerIndexReference        DellObjectRange,
    systemResourceDMAShareDisposition           DellResourceShareDisposition,
    systemResourceDMAMaximumTransferSize        DellUnsigned32BitRange,
    systemResourceDMATransferWidth              DellResourceDMATransferWidth,
    systemResourceDMABusMaster                  DellResourceDMABusMaster
}

systemResourceDMATable                          OBJECT-TYPE
    SYNTAX      SEQUENCE OF SystemResourceDMATableEntry
    ACCESS      not-accessible
    STATUS      mandatory
    DESCRIPTION
"0500.0060 This object defines the System Resource DMA Table."
    ::= { systemResourceGroup 60 }
systemResourceDMATableEntry                     OBJECT-TYPE
    SYNTAX      SystemResourceDMATableEntry
    ACCESS      not-accessible
    STATUS      mandatory
    DESCRIPTION
"0500.0060.0001 This object defines the System Resource DMA Table Entry."
    INDEX       { systemResourceDMAchassisIndex,
                  systemResourceDMAIndex }
    ::= { systemResourceDMATable 1 }

systemResourceDMAchassisIndex                   OBJECT-TYPE
    SYNTAX      DellObjectRange
    ACCESS      read-only
    STATUS      mandatory
    DESCRIPTION
"0500.0060.0001.0001 This attribute defines the index (one based) of the
associated chassis."
    ::= { systemResourceDMATableEntry 1 }
systemResourceDMAIndex                          OBJECT-TYPE
    SYNTAX      DellObjectRange
    ACCESS      read-only
    STATUS      mandatory
    DESCRIPTION
"0500.0060.0001.0002 This attribute defines the index (one based) of the
system resource DMA."
    ::= { systemResourceDMATableEntry 2 }
systemResourceDMAStateCapabilities              OBJECT-TYPE
    SYNTAX      DellStateCapabilities
    ACCESS      read-only
    STATUS      mandatory
    DESCRIPTION
"0500.0060.0001.0003 This attribute defines the state capabilities of the
system resource DMA."
    ::= { systemResourceDMATableEntry 3 }
systemResourceDMAStateSettings                  OBJECT-TYPE
    SYNTAX      DellStateSettings
    ACCESS      read-write
    STATUS      mandatory
    DESCRIPTION
"0500.0060.0001.0004 This attribute defines the state settings of the
system resource DMA."
    ::= { systemResourceDMATableEntry 4 }
systemResourceDMAStatus                         OBJECT-TYPE
    SYNTAX      DellStatus
    ACCESS      read-only
    STATUS      mandatory
    DESCRIPTION
"0500.0060.0001.0005 This attribute defines the status of the
system resource DMA."
    ::= { systemResourceDMATableEntry 5 }
systemResourceDMAOwnerIndexReference            OBJECT-TYPE
    SYNTAX      DellObjectRange
    ACCESS      read-only
    STATUS      mandatory
    DESCRIPTION
"0500.0060.0001.0006 This attribute defines the index to the associated
system resource owner for this system resource DMA."
    ::= { systemResourceDMATableEntry 6 }
systemResourceDMAShareDisposition               OBJECT-TYPE
    SYNTAX      DellResourceShareDisposition
    ACCESS      read-only
    STATUS      mandatory
    DESCRIPTION
"0500.0060.0001.0007 This attribute defines the share disposition of the
system resource DMA."
    ::= { systemResourceDMATableEntry 7 }
systemResourceDMAMaximumTransferSize            OBJECT-TYPE
    SYNTAX      DellUnsigned32BitRange
    ACCESS      read-only
    STATUS      mandatory
    DESCRIPTION
"0500.0060.0001.0008 This attribute defines the maximum size of a memory
transfer in bytes for the system resource DMA."
    ::= { systemResourceDMATableEntry 8 }
systemResourceDMATransferWidth                  OBJECT-TYPE
    SYNTAX      DellResourceDMATransferWidth
    ACCESS      read-only
    STATUS      mandatory
    DESCRIPTION
"0500.0060.0001.0009 This attribute defines the tranfer width of the
system resource DMA."
    ::= { systemResourceDMATableEntry 9 }
systemResourceDMABusMaster                      OBJECT-TYPE
    SYNTAX      DellResourceDMABusMaster
    ACCESS      read-only
    STATUS      mandatory
    DESCRIPTION
"0500.0060.0001.0010 This attribute defines the bus master capabilities
of the system resource DMA."
    ::= { systemResourceDMATableEntry 10 }


-------------------------------------------------------------------------------
-- Power Group
--
-- OID Format: 1.3.6.1.4.1.674.10892.1.600
-------------------------------------------------------------------------------


-------------------------------------------------------------------------------
-- Power Unit Table
--
-- OID Format: 1.3.6.1.4.1.674.10892.1.600.10.1.<a>.<i1>.<i2>
-------------------------------------------------------------------------------

PowerUnitTableEntry                             ::= SEQUENCE {
    powerUnitchassisIndex                       DellObjectRange,
    powerUnitIndex                              DellObjectRange,
    powerUnitStateCapabilities                  DellStateCapabilities,
    powerUnitStateSettings                      DellStateSettings,
    powerUnitRedundancyStatus                   DellStatusRedundancy,
    powerSupplyCountForRedundancy               DellObjectRange,
    powerUnitName                               DellString,
    powerUnitStatus                             DellStatus
}

powerUnitTable                                  OBJECT-TYPE
    SYNTAX      SEQUENCE OF PowerUnitTableEntry
    ACCESS      not-accessible
    STATUS      mandatory
    DESCRIPTION
"0600.0010 This object defines the Power Unit Table."
    ::= { powerGroup 10 }
powerUnitTableEntry                             OBJECT-TYPE
    SYNTAX      PowerUnitTableEntry
    ACCESS      not-accessible
    STATUS      mandatory
    DESCRIPTION
"0600.0010.0001 This object defines the Power Unit Table Entry."
    INDEX       { powerUnitchassisIndex,
                  powerUnitIndex }
    ::= { powerUnitTable 1 }

powerUnitchassisIndex                           OBJECT-TYPE
    SYNTAX      DellObjectRange
    ACCESS      read-only
    STATUS      mandatory
    DESCRIPTION
"0600.0010.0001.0001 This attribute defines the index (one based) of the
chassis."
    ::= { powerUnitTableEntry 1 }
powerUnitIndex                                  OBJECT-TYPE
    SYNTAX      DellObjectRange
    ACCESS      read-only
    STATUS      mandatory
    DESCRIPTION
"0600.0010.0001.0002 This attribute defines the index (one based) of the
power unit."
    ::= { powerUnitTableEntry 2 }
powerUnitStateCapabilities                      OBJECT-TYPE
    SYNTAX      DellStateCapabilities
    ACCESS      read-only
    STATUS      mandatory
    DESCRIPTION
"0600.0010.0001.0003 This attribute defines the state capabilities of the
power unit."
    ::= { powerUnitTableEntry 3 }
powerUnitStateSettings                          OBJECT-TYPE
    SYNTAX      DellStateSettings
    ACCESS      read-write
    STATUS      mandatory
    DESCRIPTION
"0600.0010.0001.0004 This attribute defines the state settings of the
power unit."
    ::= { powerUnitTableEntry 4 }
powerUnitRedundancyStatus                       OBJECT-TYPE
    SYNTAX      DellStatusRedundancy
    ACCESS      read-only
    STATUS      mandatory
    DESCRIPTION
"0600.0010.0001.0005 This attribute defines the redundancy status of the
power unit."
    ::= { powerUnitTableEntry 5 }
powerSupplyCountForRedundancy                   OBJECT-TYPE
    SYNTAX      DellObjectRange
    ACCESS      read-only
    STATUS      mandatory
    DESCRIPTION
"0600.0010.0001.0006 This attribute defines the total number of power supplies
required for this power unit to have full redundancy."
    ::= { powerUnitTableEntry 6 }
powerUnitName                                   OBJECT-TYPE
    SYNTAX      DellString
    ACCESS      read-only
    STATUS      mandatory
    DESCRIPTION
"0600.0010.0001.0007 This attribute defines the name of the power unit."
    ::= { powerUnitTableEntry 7 }
powerUnitStatus                                 OBJECT-TYPE
    SYNTAX      DellStatus
    ACCESS      read-only
    STATUS      mandatory
    DESCRIPTION
"0600.0010.0001.0008 This attribute defines the status of the power unit."
    ::= { powerUnitTableEntry 8 }


-------------------------------------------------------------------------------
-- Power Supply Table
--
-- OID Format: 1.3.6.1.4.1.674.10892.1.600.12.1.<a>.<i1>.<i2>
-------------------------------------------------------------------------------

DellPowerSupplyStateCapabilitiesUnique          ::= INTEGER {
    -- If 0 (zero), there are no power supply state capabilities
    -- Note: These values are bit masks, so combination values are possible.
    unknown(1),                                 -- state capabilities are unknown
    onlineCapable(2),                           -- power supply can be enabled (online) or disabled (offline)
    notReadyCapable(4)                          -- power supply can be not ready
}
DellPowerSupplyStateSettingsUnique              ::= INTEGER {
    -- If 0 (zero), there are no power supply state settings
    -- Note: These values are bit masks, so combination values are possible.
    unknown(1),                                 -- state settings are unknown
    onLine(2),                                  -- power supply is enabled (online)
    notReady(4),                                -- power supply is not ready
    fanFailure(8),                              -- power supply fan has failed
    onlineAndFanFailure(10),
    powerSupplyIsON(16),                        -- power supply is supplying power
    powerSupplyIsOK(32),                        -- power supply is indicating it is OK
    acSwitchIsON(64),                           -- power supply is indicating AC power switch is on
    onlineandAcSwitchIsON(66),
    acPowerIsON(128),                           -- power supply is indicating AC power is on
    onlineAndAcPowerIsON(130),
    onlineAndPredictiveFailure(210),
    acPowerAndSwitchAreOnPowerSupplyIsOnIsOkAndOnline(242)
}
DellPowerSupplyType                             ::= INTEGER {
    powerSupplyTypeIsOther(1),                  -- type is other than following values
    powerSupplyTypeIsUnknown(2),                -- type is unknown
    powerSupplyTypeIsLinear(3),                 -- type is Linear
    powerSupplyTypeIsSwitching(4),              -- type is Switching
    powerSupplyTypeIsBattery(5),                -- type is Battery
    powerSupplyTypeIsUPS(6),                    -- type is Uninterruptible Power Supply
    powerSupplyTypeIsConverter(7),              -- type is Converter
    powerSupplyTypeIsRegulator(8),              -- type is Regulator
    powerSupplyTypeIsAC(9),                     -- type is AC
    powerSupplyTypeIsDC(10),                    -- type is DC
    powerSupplyTypeIsVRM(11)                    -- type is VRM
}
DellPowerSupplySensorState                      ::= INTEGER {
    -- Note: These values are bit masks, so combination values are possible.
    presenceDetected(1),                        -- state is Presence detected
    psFailureDetected(2),                       -- state is PS Failure detected
    predictiveFailure(4),                       -- state is Predictive Failure
    psACLost(8),                                -- state is PS AC lost
    acLostOrOutOfRange(16),                     -- state is AC lost or out-of-range
    acOutOfRangeButPresent(32),                 -- state is AC out-of-range, but present
    configurationError(64)                      -- state is Configuration error
}
DellPowerSupplyConfigurationErrorType           ::= INTEGER {
    vendorMismatch(1),                          -- error type is Vendor mismatch
    revisionMismatch(2),                        -- error type is Revision mismatch
    processorMissing(3)                         -- error type is Processor missing
}

PowerSupplyTableEntry                           ::= SEQUENCE {
    powerSupplychassisIndex                     DellObjectRange,
    powerSupplyIndex                            DellObjectRange,
    powerSupplyStateCapabilitiesUnique          DellPowerSupplyStateCapabilitiesUnique,
    powerSupplyStateSettingsUnique              DellPowerSupplyStateSettingsUnique,
    powerSupplyStatus                           DellStatus,
    powerSupplyOutputWatts                      DellSigned32BitRange,
    powerSupplyType                             DellPowerSupplyType,
    powerSupplyLocationName                     DellString,
    powerSupplyInputVoltage                     DellSigned32BitRange,
    powerSupplypowerUnitIndexReference          DellObjectRange,
    powerSupplySensorState                      DellPowerSupplySensorState,
    powerSupplyConfigurationErrorType           DellPowerSupplyConfigurationErrorType,
    powerSupplyPowerMonitorCapable              DellBoolean,
    powerSupplyRatedInputWattage                DellSigned32BitRange
}

powerSupplyTable                                OBJECT-TYPE
    SYNTAX      SEQUENCE OF PowerSupplyTableEntry
    ACCESS      not-accessible
    STATUS      mandatory
    DESCRIPTION
"0600.0012 This object defines the Power Supply Table."
    ::= { powerGroup 12 }
powerSupplyTableEntry                           OBJECT-TYPE
    SYNTAX      PowerSupplyTableEntry
    ACCESS      not-accessible
    STATUS      mandatory
    DESCRIPTION
"0600.0012.0001 This object defines the Power Supply Table Entry."
    INDEX       { powerSupplychassisIndex,
                  powerSupplyIndex }
    ::= { powerSupplyTable 1 }

powerSupplychassisIndex                         OBJECT-TYPE
    SYNTAX      DellObjectRange
    ACCESS      read-only
    STATUS      mandatory
    DESCRIPTION
"0600.0012.0001.0001 This attribute defines the index (one based) of the
chassis."
    ::= { powerSupplyTableEntry 1 }
powerSupplyIndex                                OBJECT-TYPE
    SYNTAX      DellObjectRange
    ACCESS      read-only
    STATUS      mandatory
    DESCRIPTION
"0600.0012.0001.0002 This attribute defines the index (one based) of the
power supply."
    ::= { powerSupplyTableEntry 2 }
powerSupplyStateCapabilitiesUnique              OBJECT-TYPE
    SYNTAX      DellPowerSupplyStateCapabilitiesUnique
    ACCESS      read-only
    STATUS      mandatory
    DESCRIPTION
"0600.0012.0001.0003 This attribute defines the state capabilities of the
power supply."
    ::= { powerSupplyTableEntry 3 }
powerSupplyStateSettingsUnique                  OBJECT-TYPE
    SYNTAX      DellPowerSupplyStateSettingsUnique
    ACCESS      read-write
    STATUS      mandatory
    DESCRIPTION
"0600.0012.0001.0004 This attribute defines the state settings of the
power supply."
    ::= { powerSupplyTableEntry 4 }
powerSupplyStatus                               OBJECT-TYPE
    SYNTAX      DellStatus
    ACCESS      read-only
    STATUS      mandatory
    DESCRIPTION
"0600.0012.0001.0005 This attribute defines the status of the power supply."
    ::= { powerSupplyTableEntry 5 }
powerSupplyOutputWatts                          OBJECT-TYPE
    SYNTAX      DellSigned32BitRange
    ACCESS      read-only
    STATUS      mandatory
    DESCRIPTION
"0600.0012.0001.0006 This attribute defines the maximum sustained output
wattage of the power supply (in tenths of Watts)."
    ::= { powerSupplyTableEntry 6 }
powerSupplyType                                 OBJECT-TYPE
    SYNTAX      DellPowerSupplyType
    ACCESS      read-only
    STATUS      mandatory
    DESCRIPTION
"0600.0012.0001.0007 This attribute defines the type of the power supply."
    ::= { powerSupplyTableEntry 7 }
powerSupplyLocationName                         OBJECT-TYPE
    SYNTAX      DellString
    ACCESS      read-only
    STATUS      mandatory
    DESCRIPTION
"0600.0012.0001.0008 This attribute defines the location of the power supply."
    ::= { powerSupplyTableEntry 8 }
powerSupplyInputVoltage                         OBJECT-TYPE
    SYNTAX      DellSigned32BitRange
    ACCESS      read-only
    STATUS      mandatory
    DESCRIPTION
"0600.0012.0001.0009 This attribute defines the input voltage to the power
supply (in Volts)."
    ::= { powerSupplyTableEntry 9 }
powerSupplypowerUnitIndexReference              OBJECT-TYPE
    SYNTAX      DellObjectRange
    ACCESS      read-only
    STATUS      mandatory
    DESCRIPTION
"0600.0012.0001.0010 This attribute defines the index to the associated
power unit if the power supply is part of a power unit."
    ::= { powerSupplyTableEntry 10 }
powerSupplySensorState                          OBJECT-TYPE
    SYNTAX      DellPowerSupplySensorState
    ACCESS      read-only
    STATUS      mandatory
    DESCRIPTION
"0600.0012.0001.0011 This attribute defines the state reported by the
power supply sensor.  This attribute supplements the attribute
powerSupplyStateSettingsUnique."
    ::= { powerSupplyTableEntry 11 }
powerSupplyConfigurationErrorType               OBJECT-TYPE
    SYNTAX      DellPowerSupplyConfigurationErrorType
    ACCESS      read-only
    STATUS      mandatory
    DESCRIPTION
"0600.0012.0001.0012 This attribute defines the type of configuration error
reported by the power supply sensor.  When the configurationError bit is on
in the value for the attribute powerSupplySensorState, a value is returned
for this attribute; otherwise, a value is not returned for this attribute."
    ::= { powerSupplyTableEntry 12 }
powerSupplyPowerMonitorCapable                  OBJECT-TYPE
    SYNTAX      DellBoolean
    ACCESS      read-only
    STATUS      mandatory
    DESCRIPTION
"0600.0012.0001.0013 This attribute defines a boolean value that reports
whether the power supply is capable of monitoring power consumption."
    ::= { powerSupplyTableEntry 13 }
powerSupplyRatedInputWattage                    OBJECT-TYPE
    SYNTAX      DellSigned32BitRange
    ACCESS      read-only
    STATUS      mandatory
    DESCRIPTION
"0600.0012.0001.0014 This attribute defines the rated input wattage of the
power supply (in tenths of Watts)."
    ::= { powerSupplyTableEntry 14 }


-------------------------------------------------------------------------------
-- Voltage Probe Table
--
-- OID Format: 1.3.6.1.4.1.674.10892.1.600.20.1.<a>.<i1>.<i2>
-------------------------------------------------------------------------------

DellVoltageType                                 ::= INTEGER {
    voltageProbeTypeIsOther(1),                 -- type is other than following values
    voltageProbeTypeIsUnknown(2),               -- type is unknown
    voltageProbeTypeIs1Point5Volt(3),           -- type is 1.5 volt probe
    voltageProbeTypeIs3Point3Volt(4),           -- type is 3.3 volt probe
    voltageProbeTypeIs5Volt(5),                 -- type is 5 volt probe
    voltageProbeTypeIsMinus5Volt(6),            -- type is -5 volt probe
    voltageProbeTypeIs12Volt(7),                -- type is 12 volt probe
    voltageProbeTypeIsMinus12Volt(8),           -- type is -12 volt probe
    voltageProbeTypeIsIO(9),                    -- type is I/O probe
    voltageProbeTypeIsCore(10),                 -- type is Core probe
    voltageProbeTypeIsFLEA(11),                 -- type is FLEA (standby) probe
    voltageProbeTypeIsBattery(12),              -- type is Battery probe
    voltageProbeTypeIsTerminator(13),           -- type is SCSI Termination probe
    voltageProbeTypeIs2Point5Volt(14),          -- type is 2.5 volt probe
    voltageProbeTypeIsGTL(15),                  -- type is GTL (ground termination logic) probe
    voltageProbeTypeIsDiscrete(16)              -- type is voltage probe with discrete reading
}
DellVoltageDiscreteReading                      ::= INTEGER {
    voltageIsGood(1),                           -- voltage reading is Good
    voltageIsBad(2)                             -- voltage reading is Bad
}

VoltageProbeTableEntry                          ::= SEQUENCE {
    voltageProbechassisIndex                    DellObjectRange,
    voltageProbeIndex                           DellObjectRange,
    voltageProbeStateCapabilities               DellStateCapabilities,
    voltageProbeStateSettings                   DellStateSettings,
    voltageProbeStatus                          DellStatusProbe,
    voltageProbeReading                         DellSigned32BitRange,
    voltageProbeType                            DellVoltageType,
    voltageProbeLocationName                    DellString,
    voltageProbeUpperNonRecoverableThreshold    DellSigned32BitRange,
    voltageProbeUpperCriticalThreshold          DellSigned32BitRange,
    voltageProbeUpperNonCriticalThreshold       DellSigned32BitRange,
    voltageProbeLowerNonCriticalThreshold       DellSigned32BitRange,
    voltageProbeLowerCriticalThreshold          DellSigned32BitRange,
    voltageProbeLowerNonRecoverableThreshold    DellSigned32BitRange,
    voltageProbeProbeCapabilities               DellProbeCapabilities,
    voltageProbeDiscreteReading                 DellVoltageDiscreteReading
}

voltageProbeTable                               OBJECT-TYPE
    SYNTAX      SEQUENCE OF VoltageProbeTableEntry
    ACCESS      not-accessible
    STATUS      mandatory
    DESCRIPTION
"0600.0020 This object defines the Voltage Probe Table."
    ::= { powerGroup 20 }
voltageProbeTableEntry                          OBJECT-TYPE
    SYNTAX      VoltageProbeTableEntry
    ACCESS      not-accessible
    STATUS      mandatory
    DESCRIPTION
"0600.0020.001 This object defines the Voltage Probe Table Entry."
    INDEX       { voltageProbechassisIndex,
                  voltageProbeIndex }
    ::= { voltageProbeTable 1 }

voltageProbechassisIndex                        OBJECT-TYPE
    SYNTAX      DellObjectRange
    ACCESS      read-only
    STATUS      mandatory
    DESCRIPTION
"0600.0020.0001.0001 This attribute defines the index (one based) of the
chassis."
    ::= { voltageProbeTableEntry 1 }
voltageProbeIndex                               OBJECT-TYPE
    SYNTAX      DellObjectRange
    ACCESS      read-only
    STATUS      mandatory
    DESCRIPTION
"0600.0020.0001.0002 This attribute defines the index (one based) of the
voltage probe."
    ::= { voltageProbeTableEntry 2 }
voltageProbeStateCapabilities                   OBJECT-TYPE
    SYNTAX      DellStateCapabilities
    ACCESS      read-only
    STATUS      mandatory
    DESCRIPTION
"0600.0020.0001.0003 This attribute defines the state capabilities of the
voltage probe."
    ::= { voltageProbeTableEntry 3 }
voltageProbeStateSettings                       OBJECT-TYPE
    SYNTAX      DellStateSettings
    ACCESS      read-write
    STATUS      mandatory
    DESCRIPTION
"0600.0020.0001.0004 This attribute defines the state settings of the
voltage probe."
    ::= { voltageProbeTableEntry 4 }
voltageProbeStatus                              OBJECT-TYPE
    SYNTAX      DellStatusProbe
    ACCESS      read-only
    STATUS      mandatory
    DESCRIPTION
"0600.0020.0001.0005 This attribute defines the probe status of the
voltage probe."
    ::= { voltageProbeTableEntry 5 }
voltageProbeReading                             OBJECT-TYPE
    SYNTAX      DellSigned32BitRange
    ACCESS      read-only
    STATUS      mandatory
    DESCRIPTION
"0600.0020.0001.0006 This attribute defines the reading for a voltage
probe of type other than voltageProbeTypeIsDiscrete.  When the value
for voltageProbeType is other than voltageProbeTypeIsDiscrete, the value
returned for this attribute is the voltage that the probe is reading
in millivolts.  When the value for voltageProbeType is
voltageProbeTypeIsDiscrete, a value is not returned for this attribute."
    ::= { voltageProbeTableEntry 6 }
voltageProbeType                                OBJECT-TYPE
    SYNTAX      DellVoltageType
    ACCESS      read-only
    STATUS      mandatory
    DESCRIPTION
"0600.0020.0001.0007 This attribute defines the type of the voltage probe."
    ::= { voltageProbeTableEntry 7 }
voltageProbeLocationName                        OBJECT-TYPE
    SYNTAX      DellString
    ACCESS      read-only
    STATUS      mandatory
    DESCRIPTION
"0600.0020.0001.0008 This attribute defines the location name of the
voltage probe."
    ::= { voltageProbeTableEntry 8 }
voltageProbeUpperNonRecoverableThreshold        OBJECT-TYPE
    SYNTAX      DellSigned32BitRange
    ACCESS      read-only
    STATUS      mandatory
    DESCRIPTION
"0600.0020.0001.0009 This attribute defines the upper nonrecoverable threshold
of the voltage probe.  The value is an integer representing the voltage
of the threshold in millivolts."
    ::= { voltageProbeTableEntry 9 }
voltageProbeUpperCriticalThreshold              OBJECT-TYPE
    SYNTAX      DellSigned32BitRange
    ACCESS      read-only
    STATUS      mandatory
    DESCRIPTION
"0600.0020.0001.0010 This attribute defines the upper critical threshold
of the voltage probe.  The value is an integer representing the voltage
of the threshold in millivolts."
    ::= { voltageProbeTableEntry 10 }
voltageProbeUpperNonCriticalThreshold           OBJECT-TYPE
    SYNTAX      DellSigned32BitRange
    ACCESS      read-write
    STATUS      mandatory
    DESCRIPTION
"0600.0020.0001.0011 This attribute defines the upper noncritical threshold
of the voltage probe.  The value is an integer representing the voltage
of the threshold in millivolts."
    ::= { voltageProbeTableEntry 11 }
voltageProbeLowerNonCriticalThreshold           OBJECT-TYPE
    SYNTAX      DellSigned32BitRange
    ACCESS      read-write
    STATUS      mandatory
    DESCRIPTION
"0600.0020.0001.0012 This attribute defines the lower noncritical threshold
of the voltage probe.  The value is an integer representing the voltage
of the threshold in millivolts."
    ::= { voltageProbeTableEntry 12 }
voltageProbeLowerCriticalThreshold              OBJECT-TYPE
    SYNTAX      DellSigned32BitRange
    ACCESS      read-only
    STATUS      mandatory
    DESCRIPTION
"0600.0020.0001.0013 This attribute defines the lower critical threshold
of the voltage probe.  The value is an integer representing the voltage
of the threshold in millivolts."
    ::= { voltageProbeTableEntry 13 }
voltageProbeLowerNonRecoverableThreshold        OBJECT-TYPE
    SYNTAX      DellSigned32BitRange
    ACCESS      read-only
    STATUS      mandatory
    DESCRIPTION
"0600.0020.0001.0014 This attribute defines the lower nonrecoverable threshold
of the voltage probe.  The value is an integer representing the voltage
of the threshold in millivolts."
    ::= { voltageProbeTableEntry 14 }
voltageProbeProbeCapabilities                   OBJECT-TYPE
    SYNTAX      DellProbeCapabilities
    ACCESS      read-only
    STATUS      mandatory
    DESCRIPTION
"0600.0020.0001.0015 This attribute defines the probe capabilities of the
voltage probe."
    ::= { voltageProbeTableEntry 15 }
voltageProbeDiscreteReading                     OBJECT-TYPE
    SYNTAX      DellVoltageDiscreteReading
    ACCESS      read-only
    STATUS      mandatory
    DESCRIPTION
"0600.0020.0001.0016 This attribute defines the reading for a voltage
probe of type voltageProbeTypeIsDiscrete.  When the value for voltageProbeType
is other than voltageProbeTypeIsDiscrete, a value is not returned for this
attribute.  When the value for voltageProbeType is voltageProbeTypeIsDiscrete,
the value returned for this attribute is the discrete reading for the probe."
    ::= { voltageProbeTableEntry 16 }


-------------------------------------------------------------------------------
-- Amperage Probe Table
--
-- OID Format: 1.3.6.1.4.1.674.10892.1.600.30.1.<a>.<i1>.<i2>
-------------------------------------------------------------------------------

DellAmperageProbeType    ::= INTEGER {
    amperageProbeTypeIsOther(1),                -- type is other than following values
    amperageProbeTypeIsUnknown(2),              -- type is unknown
    amperageProbeTypeIs1Point5Volt(3),          -- type is 1.5 amperage probe
    amperageProbeTypeIs3Point3volt(4),          -- type is 3.3 amperage probe
    amperageProbeTypeIs5Volt(5),                -- type is 5 amperage probe
    amperageProbeTypeIsMinus5Volt(6),           -- type is -5 amperage probe
    amperageProbeTypeIs12Volt(7),               -- type is 12 amperage probe
    amperageProbeTypeIsMinus12Volt(8),          -- type is -12 amperage probe
    amperageProbeTypeIsIO(9),                   -- type is I/O probe
    amperageProbeTypeIsCore(10),                -- type is Core probe
    amperageProbeTypeIsFLEA(11),                -- type is FLEA (standby) probe
    amperageProbeTypeIsBattery(12),             -- type is Battery probe
    amperageProbeTypeIsTerminator(13),          -- type is SCSI Termination probe
    amperageProbeTypeIs2Point5Volt(14),         -- type is 2.5 amperage probe
    amperageProbeTypeIsGTL(15),                 -- type is GTL (ground termination logic) probe
    amperageProbeTypeIsDiscrete(16),            -- type is amperage probe with discrete reading
    amperageProbeTypeIsPowerSupplyAmps(23),     -- type is Power Supply probe with reading in Amps
    amperageProbeTypeIsPowerSupplyWatts(24),    -- type is Power Supply probe with reading in Watts
    amperageProbeTypeIsSystemAmps(25),          -- type is System probe with reading in Amps
    amperageProbeTypeIsSystemWatts(26)          -- type is System probe with reading in Watts
}
DellAmperageDiscreteReading                     ::= INTEGER {
    amperageIsGood(1),                          -- amperage reading is Good
    amperageIsBad(2)                            -- amperage reading is Bad
}

AmperageProbeTableEntry                         ::= SEQUENCE {
    amperageProbechassisIndex                   DellObjectRange,
    amperageProbeIndex                          DellObjectRange,
    amperageProbeStateCapabilities              DellStateCapabilities,
    amperageProbeStateSettings                  DellStateSettings,
    amperageProbeStatus                         DellStatusProbe,
    amperageProbeReading                        DellSigned32BitRange,
    amperageProbeType                           DellAmperageProbeType,
    amperageProbeLocationName                   DellString,
    amperageProbeUpperNonRecoverableThreshold   DellSigned32BitRange,
    amperageProbeUpperCriticalThreshold         DellSigned32BitRange,
    amperageProbeUpperNonCriticalThreshold      DellSigned32BitRange,
    amperageProbeLowerNonCriticalThreshold      DellSigned32BitRange,
    amperageProbeLowerCriticalThreshold         DellSigned32BitRange,
    amperageProbeLowerNonRecoverableThreshold   DellSigned32BitRange,
    amperageProbeProbeCapabilities              DellProbeCapabilities,
    amperageProbeDiscreteReading                DellAmperageDiscreteReading
}

amperageProbeTable                              OBJECT-TYPE
    SYNTAX      SEQUENCE OF AmperageProbeTableEntry
    ACCESS      not-accessible
    STATUS      mandatory
    DESCRIPTION
"0600.0030 This object defines the Amperage Probe Table."
    ::= { powerGroup 30 }
amperageProbeTableEntry                         OBJECT-TYPE
    SYNTAX      AmperageProbeTableEntry
    ACCESS      not-accessible
    STATUS      mandatory
    DESCRIPTION
"0600.0030.0001 This object defines the Amperage Probe Table Entry."
    INDEX       { amperageProbechassisIndex,
                  amperageProbeIndex }
    ::= { amperageProbeTable 1 }

amperageProbechassisIndex                       OBJECT-TYPE
    SYNTAX      DellObjectRange
    ACCESS      read-only
    STATUS      mandatory
    DESCRIPTION
"0600.0030.0001.0001 This attribute defines the index (one based) of the
chassis."
    ::= { amperageProbeTableEntry 1 }
amperageProbeIndex                              OBJECT-TYPE
    SYNTAX      DellObjectRange
    ACCESS      read-only
    STATUS      mandatory
    DESCRIPTION
"0600.0030.0001.0002 This attribute defines the index (one based) of the
amperage probe."
    ::= { amperageProbeTableEntry 2 }
amperageProbeStateCapabilities                  OBJECT-TYPE
    SYNTAX      DellStateCapabilities
    ACCESS      read-only
    STATUS      mandatory
    DESCRIPTION
"0600.0030.0001.0003 This attribute defines the state capabilities of the
amperage probe."
    ::= { amperageProbeTableEntry 3 }
amperageProbeStateSettings                      OBJECT-TYPE
    SYNTAX      DellStateSettings
    ACCESS      read-write
    STATUS      mandatory
    DESCRIPTION
"0600.0030.0001.0004 This attribute defines the state settings of the
amperage probe."
    ::= { amperageProbeTableEntry 4 }
amperageProbeStatus                             OBJECT-TYPE
    SYNTAX      DellStatusProbe
    ACCESS      read-only
    STATUS      mandatory
    DESCRIPTION
"0600.0030.0001.0005 This attribute defines the probe status of the
amperage probe."
    ::= { amperageProbeTableEntry 5 }
amperageProbeReading                            OBJECT-TYPE
    SYNTAX      DellSigned32BitRange
    ACCESS      read-only
    STATUS      mandatory
    DESCRIPTION
"0600.0030.0001.0006 This attribute defines the reading for an amperage
probe of type other than amperageProbeTypeIsDiscrete.

When the value for amperageProbeType is amperageProbeTypeIsPowerSupplyAmps
or amperageProbeTypeIsSystemAmps, the value returned for this attribute
is the power usage that the probe is reading in tenths of Amps.

When the value for amperageProbeType is amperageProbeTypeIsPowerSupplyWatts
or amperageProbeTypeIsSystemWatts, the value returned for this attribute
is the power usage that the probe is reading in Watts.

When the value for amperageProbeType is other than amperageProbeTypeIsDiscrete,
amperageProbeTypeIsPowerSupplyAmps, amperageProbeTypeIsPowerSupplyWatts,
amperageProbeTypeIsSystemAmps or amperageProbeTypeIsSystemWatts,
the value returned for this attribute is the amperage that the probe is
reading in Milliamps.

When the value for amperageProbeType is amperageProbeTypeIsDiscrete,
a value is not returned for this attribute."
    ::= { amperageProbeTableEntry 6 }
amperageProbeType                               OBJECT-TYPE
    SYNTAX      DellAmperageProbeType
    ACCESS      read-only
    STATUS      mandatory
    DESCRIPTION
"0600.0030.0001.0007 This attribute defines the type of the amperage probe."
    ::= { amperageProbeTableEntry 7 }
amperageProbeLocationName                       OBJECT-TYPE
    SYNTAX      DellString
    ACCESS      read-only
    STATUS      mandatory
    DESCRIPTION
"0600.0030.0001.0008 This attribute defines the location of the amperage probe."
    ::= { amperageProbeTableEntry 8 }
amperageProbeUpperNonRecoverableThreshold       OBJECT-TYPE
    SYNTAX      DellSigned32BitRange
    ACCESS      read-only
    STATUS      mandatory
    DESCRIPTION
"0600.0030.0001.0009 This attribute defines the upper nonrecoverable threshold
of the amperage probe.  The value is an integer representing the amperage
of the threshold in milliamps."
    ::= { amperageProbeTableEntry 9 }
amperageProbeUpperCriticalThreshold             OBJECT-TYPE
    SYNTAX      DellSigned32BitRange
    ACCESS      read-only
    STATUS      mandatory
    DESCRIPTION
"0600.0030.0001.0010 This attribute defines the upper critical threshold
of the amperage probe.  The value is an integer representing the amperage
of the threshold in milliamps."
    ::= { amperageProbeTableEntry 10 }
amperageProbeUpperNonCriticalThreshold          OBJECT-TYPE
    SYNTAX      DellSigned32BitRange
    ACCESS      read-write
    STATUS      mandatory
    DESCRIPTION
"0600.0030.0001.0011 This attribute defines the upper noncritical threshold
of the amperage probe.  The value is an integer representing the amperage
of the threshold in milliamps."
    ::= { amperageProbeTableEntry 11 }
amperageProbeLowerNonCriticalThreshold          OBJECT-TYPE
    SYNTAX      DellSigned32BitRange
    ACCESS      read-write
    STATUS      mandatory
    DESCRIPTION
"0600.0030.0001.0012 This attribute defines the lower noncritical threshold
of the amperage probe.  The value is an integer representing the amperage
of the threshold in milliamps."
    ::= { amperageProbeTableEntry 12 }
amperageProbeLowerCriticalThreshold             OBJECT-TYPE
    SYNTAX      DellSigned32BitRange
    ACCESS      read-only
    STATUS      mandatory
    DESCRIPTION
"0600.0030.0001.0013 This attribute defines the lower critical threshold
of the amperage probe.  The value is an integer representing the amperage
of the threshold in milliamps."
    ::= { amperageProbeTableEntry 13 }
amperageProbeLowerNonRecoverableThreshold       OBJECT-TYPE
    SYNTAX      DellSigned32BitRange
    ACCESS      read-only
    STATUS      mandatory
    DESCRIPTION
"0600.0030.0001.0014 This attribute defines the lower nonrecoverable threshold
of the amperage probe.  The value is an integer representing the amperage
of the threshold in milliamps."
    ::= { amperageProbeTableEntry 14 }
amperageProbeProbeCapabilities                  OBJECT-TYPE
    SYNTAX      DellProbeCapabilities
    ACCESS      read-only
    STATUS      mandatory
    DESCRIPTION
"0600.0030.0001.0015 This attribute defines the probe capabilities of the
amperage probe."
    ::= { amperageProbeTableEntry 15 }
amperageProbeDiscreteReading                    OBJECT-TYPE
    SYNTAX      DellAmperageDiscreteReading
    ACCESS      read-only
    STATUS      mandatory
    DESCRIPTION
"0600.0030.0001.0016 This attribute defines the reading for an amperage
probe of type amperageProbeTypeIsDiscrete.  When the value for amperageProbeType
is other than amperageProbeTypeIsDiscrete, a value is not returned for this
attribute.  When the value for amperageProbeType is amperageProbeTypeIsDiscrete,
the value returned for this attribute is the discrete reading for the probe."
    ::= { amperageProbeTableEntry 16 }


-------------------------------------------------------------------------------
-- AC Power Switch Table
--
-- OID Format: 1.3.6.1.4.1.674.10892.1.600.40.1.<a>.<i1>.<i2>
-------------------------------------------------------------------------------

DellACPowerSwitchCapabilities                   ::= INTEGER {
    -- If 0 (zero), there are no AC Power Switch capabilities
    -- Note: These values are bit masks, so combination values are possible.
    unknownCapabilities(1),                     -- capabilities are unknown
    -- The objects capabilities allow it to be set to:
    inputSourceCord1NoReturnCapable(2),         -- input source can be cord 1, with no return
    inputSourceCord1ReturnCapable(4),           -- input source can be cord 1, with return
    inputSourceCord2NoReturnCapable(8),         -- input source can be cord 2, with no return
    inputSourceCord1NoReturnCord1ReturnAndCord2NoReturnCapable(14),
    inputSourceCord2ReturnCapable(16),          -- input source can be cord 2, with return
    inputSourceAllExceptSharedCapable(30),
    inputSourceSharedCapable(32),               -- input source can be shared
    inputSourceAllCapable(62)
}
DellACPowerSwitchSettings                       ::= INTEGER {
    -- If 0 (zero), there are no AC Power Switch settings
    -- Note: These values are bit masks, so combination values are possible.
    unknown(1),                                 -- settings are unknown
	-- Input source settings are mutually-exclusive
    inputSourceCord1NoReturn(2),                -- input source is cord 1, with no return
    inputSourceCord1Return(4),                  -- input source is cord 1, with return
    inputSourceCord2NoReturn(8),                -- input source is cord 2, with no return
    inputSourceCord2Return(16),                 -- input source is cord 2, with return
    inputSourceShared(32)                       -- input source is shared
}
DellACPowerSwitchRedundancyMode                 ::= INTEGER {
    nonRedundant(1),                            -- AC power switch not expecting redundancy
    redundant(2)                                -- AC power switch is expecting redundancy
}

ACPowerSwitchTableEntry                         ::= SEQUENCE {
    aCPowerSwitchchassisIndex                   DellObjectRange,
    aCPowerSwitchIndex                          DellObjectRange,
    aCPowerSwitchCapabilities                   DellACPowerSwitchCapabilities,
    aCPowerSwitchSettings                       DellACPowerSwitchSettings,
    aCPowerSwitchRedundancyStatus               DellStatusRedundancy,
    aCPowerCordCountForRedundancy               DellObjectRange,
    aCPowerSwitchName                           DellString,
    aCPowerSwitchRedundancyMode                 DellACPowerSwitchRedundancyMode,
    aCPowerSwitchStatus                         DellStatus
}

aCPowerSwitchTable                              OBJECT-TYPE
    SYNTAX      SEQUENCE OF ACPowerSwitchTableEntry
    ACCESS      not-accessible
    STATUS      mandatory
    DESCRIPTION
"0600.0040 This object defines the AC Power Switch Table."
    ::= { powerGroup 40 }
aCPowerSwitchTableEntry                         OBJECT-TYPE
    SYNTAX      ACPowerSwitchTableEntry
    ACCESS      not-accessible
    STATUS      mandatory
    DESCRIPTION
"0600.0040.0001 This object defines the AC Power Switch Table Entry."
    INDEX       { aCPowerSwitchchassisIndex,
                  aCPowerSwitchIndex }
    ::= { aCPowerSwitchTable 1 }

aCPowerSwitchchassisIndex                       OBJECT-TYPE
    SYNTAX      DellObjectRange
    ACCESS      read-only
    STATUS      mandatory
    DESCRIPTION
"0600.0040.0001.0001 This attribute defines the index (one based) of the
associated chassis."
    ::= { aCPowerSwitchTableEntry 1 }
aCPowerSwitchIndex                              OBJECT-TYPE
    SYNTAX      DellObjectRange
    ACCESS      read-only
    STATUS      mandatory
    DESCRIPTION
"0600.0040.0001.0002 This attribute defines the index (one based) of the
AC power switch."
    ::= { aCPowerSwitchTableEntry 2 }
aCPowerSwitchCapabilities                       OBJECT-TYPE
    SYNTAX      DellACPowerSwitchCapabilities
    ACCESS      read-only
    STATUS      mandatory
    DESCRIPTION
"0600.0040.0001.0003 This attribute defines the capabilities of the
AC power switch."
    ::= { aCPowerSwitchTableEntry 3 }
aCPowerSwitchSettings                           OBJECT-TYPE
    SYNTAX      DellACPowerSwitchSettings
    ACCESS      read-write
    STATUS      mandatory
    DESCRIPTION
"0600.0040.0001.0004 This attribute defines the settings of the
AC power switch."
    ::= { aCPowerSwitchTableEntry 4 }
aCPowerSwitchRedundancyStatus                   OBJECT-TYPE
    SYNTAX      DellStatusRedundancy
    ACCESS      read-only
    STATUS      mandatory
    DESCRIPTION
"0600.0040.0001.0005 This attribute defines the redundancy status of the
AC power switch."
    ::= { aCPowerSwitchTableEntry 5 }
aCPowerCordCountForRedundancy                   OBJECT-TYPE
    SYNTAX      DellObjectRange
    ACCESS      read-only
    STATUS      mandatory
    DESCRIPTION
"0600.0040.0001.0006 This attribute defines the total number of AC power
cords required for this AC power switch to have full redundancy."
    ::= { aCPowerSwitchTableEntry 6 }
aCPowerSwitchName                               OBJECT-TYPE
    SYNTAX      DellString
    ACCESS      read-only
    STATUS      mandatory
    DESCRIPTION
"0600.0040.0001.0007 This attribute defines the name of the AC power switch."
    ::= { aCPowerSwitchTableEntry 7 }
aCPowerSwitchRedundancyMode                     OBJECT-TYPE
    SYNTAX      DellACPowerSwitchRedundancyMode
    ACCESS      read-write
    STATUS      mandatory
    DESCRIPTION
"0600.0040.0001.0008 This attribute defines the redundancy mode of the
AC power switch."
    ::= { aCPowerSwitchTableEntry 8 }
aCPowerSwitchStatus                             OBJECT-TYPE
    SYNTAX      DellStatus
    ACCESS      read-only
    STATUS      mandatory
    DESCRIPTION
"0600.0040.0001.0009 This attribute defines the status of the AC power switch."
    ::= { aCPowerSwitchTableEntry 9 }


-------------------------------------------------------------------------------
-- AC Power Cord Table
--
-- OID Format: 1.3.6.1.4.1.674.10892.1.600.42.1.<a>.<i1>.<i2>
-------------------------------------------------------------------------------

DellACPowerCordStateCapabilities                ::= INTEGER {
    -- If 0 (zero), there are no AC Power Cord state capabilities
    -- Note: These values are bit masks, so combination values are possible.
    unknown(1),                                 -- state capabilities are unknown
    enableCapable(2),                           -- AC power cord can be enabled (online) or disabled (offline)
    notReadyCapable(4)                          -- AC power cord can be not ready
}
DellACPowerCordStateSettings                    ::= INTEGER {
    -- If 0 (zero), there are no AC Power Cord state settings
    -- Note: These values are bit masks, so combination values are possible.
    unknown(1),                                 -- state settings are unknown
    enabled(2),                                 -- AC power cord is enabled (online)
    notReady(4),                                -- AC power cord is not ready
    acPowerCordHasPower(8),                     -- AC power cord has power
    acPowerCordIsEnabledAndHasPower(10),
    acPowerCordIsActiveSource(16),              -- AC power cord is active source of AC power
    acPowerCordIsEnabledHasPowerAndIsActiveSource(26)
}

ACPowerCordTableEntry                           ::= SEQUENCE {
    aCPowerCordchassisIndex                     DellObjectRange,
    aCPowerCordIndex                            DellObjectRange,
    aCPowerCordStateCapabilities                DellACPowerCordStateCapabilities,
    aCPowerCordStateSettings                    DellACPowerCordStateSettings,
    aCPowerCordStatus                           DellStatus,
    aCPowerCordaCPowerSwitchIndexReference      DellObjectRange,
    aCPowerCordLocationName                     DellString
}

aCPowerCordTable                                OBJECT-TYPE
    SYNTAX      SEQUENCE OF ACPowerCordTableEntry
    ACCESS      not-accessible
    STATUS      mandatory
    DESCRIPTION
"0600.0042 This object defines the AC Power Cord Table."
    ::= { powerGroup 42 }
aCPowerCordTableEntry                           OBJECT-TYPE
    SYNTAX      ACPowerCordTableEntry
    ACCESS      not-accessible
    STATUS      mandatory
    DESCRIPTION
"0600.0042.0001 This object defines the AC Power Cord Table Entry."
    INDEX       { aCPowerCordchassisIndex,
                  aCPowerCordIndex }
    ::= { aCPowerCordTable 1 }

aCPowerCordchassisIndex                         OBJECT-TYPE
    SYNTAX      DellObjectRange
    ACCESS      read-only
    STATUS      mandatory
    DESCRIPTION
"0600.0042.0001.0001 This attribute defines the index (one based) of the
associated chassis."
    ::= { aCPowerCordTableEntry 1 }
aCPowerCordIndex                                OBJECT-TYPE
    SYNTAX      DellObjectRange
    ACCESS      read-only
    STATUS      mandatory
    DESCRIPTION
"0600.0042.0001.0002 This attribute defines the index (one based) of the
AC power cord."
    ::= { aCPowerCordTableEntry 2 }
aCPowerCordStateCapabilities                    OBJECT-TYPE
    SYNTAX      DellACPowerCordStateCapabilities
    ACCESS      read-only
    STATUS      mandatory
    DESCRIPTION
"0600.0042.0001.0003 This attribute defines the state capabilities of the
AC power cord."
    ::= { aCPowerCordTableEntry 3 }
aCPowerCordStateSettings                        OBJECT-TYPE
    SYNTAX      DellACPowerCordStateSettings
    ACCESS      read-write
    STATUS      mandatory
    DESCRIPTION
"0600.0042.0001.0004 This attribute defines the state settings of the
AC power cord."
    ::= { aCPowerCordTableEntry 4 }
aCPowerCordStatus                               OBJECT-TYPE
    SYNTAX      DellStatus
    ACCESS      read-only
    STATUS      mandatory
    DESCRIPTION
"0600.0042.0001.0005 This attribute defines the status of the AC power cord."
    ::= { aCPowerCordTableEntry 5 }
aCPowerCordaCPowerSwitchIndexReference          OBJECT-TYPE
    SYNTAX      DellObjectRange
    ACCESS      read-only
    STATUS      mandatory
    DESCRIPTION
"0600.0042.0001.0006 This attribute defines the index (one based) to the
associated AC power switch for this AC power cord."
    ::= { aCPowerCordTableEntry 6 }
aCPowerCordLocationName                         OBJECT-TYPE
    SYNTAX      DellString
    ACCESS      read-only
    STATUS      mandatory
    DESCRIPTION
"0600.0042.0001.0007 This attribute defines the location of the
AC power cord."
    ::= { aCPowerCordTableEntry 7 }


-------------------------------------------------------------------------------
-- Battery Table
--
-- OID Format: 1.3.6.1.4.1.674.10892.1.600.50.1.<a>.<i1>.<i2>
-------------------------------------------------------------------------------

DellBatteryReading                              ::= INTEGER {
    -- Note: These values are bit masks, so combination values are possible.
    predictiveFailure(1),                       -- battery predictive failure
    failed(2),                                  -- battery failed
    presenceDetected(4)                         -- battery presence detected
}

BatteryTableEntry                               ::= SEQUENCE {
    batteryChassisIndex                         DellObjectRange,
    batteryIndex                                DellObjectRange,
    batteryStateCapabilities                    DellStateCapabilities,
    batteryStateSettings                        DellStateSettings,
    batteryStatus                               DellStatus,
    batteryReading                              DellBatteryReading,
    batteryLocationName                         DellString
}

batteryTable                                    OBJECT-TYPE
    SYNTAX      SEQUENCE OF BatteryTableEntry
    ACCESS      not-accessible
    STATUS      mandatory
    DESCRIPTION
"0600.0050 This object defines the Battery Table."
    ::= { powerGroup 50 }
batteryTableEntry                               OBJECT-TYPE
    SYNTAX      BatteryTableEntry
    ACCESS      not-accessible
    STATUS      mandatory
    DESCRIPTION
"0600.0050.0001 This object defines the Battery Table Entry."
    INDEX       { batteryChassisIndex,
                  batteryIndex }
    ::= { batteryTable 1 }

batteryChassisIndex                             OBJECT-TYPE
    SYNTAX      DellObjectRange
    ACCESS      read-only
    STATUS      mandatory
    DESCRIPTION
"0600.0050.0001.0001 This attribute defines the index (one based) of the
chassis that contains the battery."
    ::= { batteryTableEntry 1 }
batteryIndex                                    OBJECT-TYPE
    SYNTAX      DellObjectRange
    ACCESS      read-only
    STATUS      mandatory
    DESCRIPTION
"0600.0050.0001.0002 This attribute defines the index (one based) of the
battery."
    ::= { batteryTableEntry 2 }
batteryStateCapabilities                        OBJECT-TYPE
    SYNTAX      DellStateCapabilities
    ACCESS      read-only
    STATUS      mandatory
    DESCRIPTION
"0600.0050.0001.0003 This attribute defines the state capabilities of the
battery."
    ::= { batteryTableEntry 3 }
batteryStateSettings                            OBJECT-TYPE
    SYNTAX      DellStateSettings
    ACCESS      read-write
    STATUS      mandatory
    DESCRIPTION
"0600.0050.0001.0004 This attribute defines the state settings of the
battery."
    ::= { batteryTableEntry 4 }
batteryStatus                                   OBJECT-TYPE
    SYNTAX      DellStatus
    ACCESS      read-only
    STATUS      mandatory
    DESCRIPTION
"0600.0050.0001.0005 This attribute defines the status of the battery."
    ::= { batteryTableEntry 5 }
batteryReading                                  OBJECT-TYPE
    SYNTAX      DellBatteryReading
    ACCESS      read-only
    STATUS      mandatory
    DESCRIPTION
"0600.0050.0001.0006 This attribute defines the reading of the battery."
    ::= { batteryTableEntry 6 }
batteryLocationName                             OBJECT-TYPE
    SYNTAX      DellString
    ACCESS      read-only
    STATUS      mandatory
    DESCRIPTION
"0600.0050.0001.0007 This attribute defines the location of the battery."
    ::= { batteryTableEntry 7 }


-------------------------------------------------------------------------------
-- Power Usage Table
--
-- OID Format: 1.3.6.1.4.1.674.10892.1.600.60.1.<a>.<i1>.<i2>
-------------------------------------------------------------------------------

DellPowerCapCapabilities                        ::= INTEGER {
    -- Note: These values are bit masks, so combination values are possible.
    -- none(0),                                 -  no power cap capabilities
    enable(1),                                  -- power cap can be enabled
    disable(2)                                  -- power cap can be disabled
}
DellPowerCapSetting                             ::= INTEGER {
    -- disabled(0),                             -  power cap disabled
    enabled(1)                                  -- power cap enabled
}

PowerUsageTableEntry                            ::= SEQUENCE {
    powerUsageChassisIndex                      DellObjectRange,
    powerUsageIndex                             DellObjectRange,
    powerUsageStateCapabilities                 DellStateCapabilities,
    powerUsageStateSettings                     DellStateSettings,
    powerUsageStatus                            DellStatus,
    powerUsageEntityName                        DellString,
    powerUsageCumulativeWattage                 DellUnsigned32BitRange,
    powerUsageCumulativeWattageStartDateName    DellDateName,
    powerUsagePeakWatts                         DellUnsigned32BitRange,
    powerUsagePeakWattsStartDateName            DellDateName,
    powerUsagePeakWattsReadingDateName          DellDateName,
    powerUsagePeakAmps                          DellUnsigned32BitRange,
    powerUsagePeakAmpsStartDateName             DellDateName,
    powerUsagePeakAmpsReadingDateName           DellDateName,
    powerUsageIdlePower                         DellUnsigned32BitRange,
    powerUsageMaxPotentialPower                 DellUnsigned32BitRange,
    powerUsagePowerCapCapabilities              DellPowerCapCapabilities,
    powerUsagePowerCapSetting                   DellPowerCapSetting,
    powerUsagePowerCapValue                     DellUnsigned32BitRange,
    powerUsageInstantaneousHeadroom             DellUnsigned32BitRange,
    powerUsagePeakHeadroom                      DellUnsigned32BitRange
}

powerUsageTable                                 OBJECT-TYPE
    SYNTAX      SEQUENCE OF PowerUsageTableEntry
    ACCESS      not-accessible
    STATUS      mandatory
    DESCRIPTION
"0600.0060 This object defines the Power Usage Table."
    ::= { powerGroup 60 }
powerUsageTableEntry                            OBJECT-TYPE
    SYNTAX      PowerUsageTableEntry
    ACCESS      not-accessible
    STATUS      mandatory
    DESCRIPTION
"0600.0060.0001 This object defines the Power Usage Table Entry."
    INDEX       { powerUsageChassisIndex,
                  powerUsageIndex }
    ::= { powerUsageTable 1 }

powerUsageChassisIndex                          OBJECT-TYPE
    SYNTAX      DellObjectRange
    ACCESS      read-only
    STATUS      mandatory
    DESCRIPTION
"0600.0060.0001.0001 This attribute defines the index (one based) of the
associated chassis."
    ::= { powerUsageTableEntry 1 }
powerUsageIndex                                 OBJECT-TYPE
    SYNTAX      DellObjectRange
    ACCESS      read-only
    STATUS      mandatory
    DESCRIPTION
"0600.0060.0001.0002 This attribute defines the index (one based) of the
power usage information."
    ::= { powerUsageTableEntry 2 }
powerUsageStateCapabilities                     OBJECT-TYPE
    SYNTAX      DellStateCapabilities
    ACCESS      read-only
    STATUS      mandatory
    DESCRIPTION
"0600.0060.0001.0003 This attribute defines the state capabilities of the
power usage information."
    ::= { powerUsageTableEntry 3 }
powerUsageStateSettings                         OBJECT-TYPE
    SYNTAX      DellStateSettings
    ACCESS      read-write
    STATUS      mandatory
    DESCRIPTION
"0600.0060.0001.0004 This attribute defines the state settings of the
power usage information."
    ::= { powerUsageTableEntry 4 }
powerUsageStatus                                OBJECT-TYPE
    SYNTAX      DellStatus
    ACCESS      read-only
    STATUS      mandatory
    DESCRIPTION
"0600.0060.0001.0005 This attribute defines the status of the
power usage information."
    ::= { powerUsageTableEntry 5 }
powerUsageEntityName                            OBJECT-TYPE
    SYNTAX      DellString
    ACCESS      read-only
    STATUS      mandatory
    DESCRIPTION
"0600.0060.0001.0006 This attribute defines the name of the entity
associated with this power usage information."
    ::= { powerUsageTableEntry 6 }
powerUsageCumulativeWattage                     OBJECT-TYPE
    SYNTAX      DellUnsigned32BitRange
    ACCESS      read-only
    STATUS      mandatory
    DESCRIPTION
"0600.0060.0001.0007 This attribute defines the total wattage used
(in Watt-hours) by this entity since the date and time specified
by the powerUsageCumulativeWattageStartDateName attribute."
    ::= { powerUsageTableEntry 7 }
powerUsageCumulativeWattageStartDateName        OBJECT-TYPE
    SYNTAX      DellDateName
    ACCESS      read-only
    STATUS      mandatory
    DESCRIPTION
"0600.0060.0001.0008 This attribute defines the date and time at
which the data collection started for the value reported by the 
powerUsageCumulativeWattage attribute."
    ::= { powerUsageTableEntry 8 }
powerUsagePeakWatts                             OBJECT-TYPE
    SYNTAX      DellUnsigned32BitRange
    ACCESS      read-only
    STATUS      mandatory
    DESCRIPTION
"0600.0060.0001.0009 This attribute defines the peak wattage reading
(in Watts) for this entity since the date and time specified by the
powerUsagePeakWattsStartDateName attribute."
    ::= { powerUsageTableEntry 9 }
powerUsagePeakWattsStartDateName                OBJECT-TYPE
    SYNTAX      DellDateName
    ACCESS      read-only
    STATUS      mandatory
    DESCRIPTION
"0600.0060.0001.0010 This attribute defines the date and time at
which the data collection started for the value reported by the 
powerUsagePeakWatts attribute."
    ::= { powerUsageTableEntry 10 }
powerUsagePeakWattsReadingDateName              OBJECT-TYPE
    SYNTAX      DellDateName
    ACCESS      read-only
    STATUS      mandatory
    DESCRIPTION
"0600.0060.0001.0011 This attribute defines the date and time at
which the value reported by the powerUsagePeakWatts attribute was
measured."
    ::= { powerUsageTableEntry 11 }
powerUsagePeakAmps                              OBJECT-TYPE
    SYNTAX      DellUnsigned32BitRange
    ACCESS      read-only
    STATUS      mandatory
    DESCRIPTION
"0600.0060.0001.0012 This attribute defines the peak amperage reading
(in tenths of Amps) for this entity since the date and time specified
by the powerUsagePeakAmpsStartDateName attribute."
    ::= { powerUsageTableEntry 12 }
powerUsagePeakAmpsStartDateName                 OBJECT-TYPE
    SYNTAX      DellDateName
    ACCESS      read-only
    STATUS      mandatory
    DESCRIPTION
"0600.0060.0001.0013 This attribute defines the date and time at
which the data collection started for the value reported by the 
powerUsagePeakAmps attribute."
    ::= { powerUsageTableEntry 13 }
powerUsagePeakAmpsReadingDateName               OBJECT-TYPE
    SYNTAX      DellDateName
    ACCESS      read-only
    STATUS      mandatory
    DESCRIPTION
"0600.0060.0001.0014 This attribute defines the date and time at
which the value reported by the powerUsagePeakAmps attribute was
measured."
    ::= { powerUsageTableEntry 14 }
powerUsageIdlePower                             OBJECT-TYPE
    SYNTAX      DellUnsigned32BitRange
    ACCESS      read-only
    STATUS      mandatory
    DESCRIPTION
"0600.0060.0001.0015 This attribute defines the system idle power
(in Watts).  This is the minimum power the system can consume
based on the current hardware configuration."
    ::= { powerUsageTableEntry 15 }
powerUsageMaxPotentialPower                     OBJECT-TYPE
    SYNTAX      DellUnsigned32BitRange
    ACCESS      read-only
    STATUS      mandatory
    DESCRIPTION
"0600.0060.0001.0016 This attribute defines the system maximum potential
power (in Watts).  This is the maximum power the system can consume
based on the current hardware configuration."
    ::= { powerUsageTableEntry 16 }
powerUsagePowerCapCapabilities                  OBJECT-TYPE
    SYNTAX      DellPowerCapCapabilities
    ACCESS      read-only
    STATUS      mandatory
    DESCRIPTION
"0600.0060.0001.0017 This attribute defines the system power cap capabilities."
    ::= { powerUsageTableEntry 17 }
powerUsagePowerCapSetting                       OBJECT-TYPE
    SYNTAX      DellPowerCapSetting
    ACCESS      read-only
    STATUS      mandatory
    DESCRIPTION
"0600.0060.0001.0018 This attribute defines the system power cap setting."
    ::= { powerUsageTableEntry 18 }
powerUsagePowerCapValue                         OBJECT-TYPE
    SYNTAX      DellUnsigned32BitRange
    ACCESS      read-only
    STATUS      mandatory
    DESCRIPTION
"0600.0060.0001.0019 This attribute defines the system power cap value
(in Watts)."
    ::= { powerUsageTableEntry 19 }
powerUsageInstantaneousHeadroom                 OBJECT-TYPE
    SYNTAX      DellUnsigned32BitRange
    ACCESS      read-only
    STATUS      mandatory
    DESCRIPTION
"0600.0060.0001.0020 This attribute defines the system instantaneous
headroom (in Watts).  This is the theoretical maximum power drawn by
the power supply minus instantaneous power draw."
    ::= { powerUsageTableEntry 20 }
powerUsagePeakHeadroom                          OBJECT-TYPE
    SYNTAX      DellUnsigned32BitRange
    ACCESS      read-only
    STATUS      mandatory
    DESCRIPTION
"0600.0060.0001.0021 This attribute defines the system peak headroom
(in Watts).  This is the theoretical maximum power drawn by the power
supply minus peak power draw."
    ::= { powerUsageTableEntry 21 }


-------------------------------------------------------------------------------
-- Power Profile Table
--
-- OID Format: 1.3.6.1.4.1.674.10892.1.600.70.1.<a>.<i1>.<i2>
-------------------------------------------------------------------------------

DellPowerProfileType                            ::= INTEGER {
    -- Note: These values are bit masks, so combination values are possible.
    -- none(0),                                 -  none
    maxPerformance(1),                          -- Maximum Performance
    osControl(2),                               -- OS Control
    activePowerController(4),                   -- Active Power Controller
    custom(8)                                   -- Custom
}
DellCPUPowerPerformanceManagementType           ::= INTEGER {
    -- Note: These values are bit masks, so combination values are possible.
    -- none(0),                                 -  none
    maxPerformance(1),                          -- Maximum Performance
    minPower(2),                                -- Minimum Power
    osDBPM(4),                                  -- OS Demand Based Power Management
    systemDBPM(8)                               -- System Demand Based Power Management
}
DellMemoryPowerPerformanceManagementType        ::= INTEGER {
    -- Note: These values are bit masks, so combination values are possible.
    -- none(0),                                 -  none
    maxPerformance(1),                          -- Maximum Performance
    mhz1333(2),                                 -- 1333 MHz
    mhz1067(4),                                 -- 1067 MHz
    mhz800(8),                                  -- 800 MHz
    minPower(16)                                -- Minimum Power
}
DellFanPowerPerformanceManagementType           ::= INTEGER {
    -- Note: These values are bit masks, so combination values are possible.
    -- none(0),                                 -  none
    maxPerformance(1),                          -- Maximum Performance
    minPower(2)                                 -- Minimum Power
}

PowerProfileTableEntry                          ::= SEQUENCE {
    powerProfileChassisIndex                    DellObjectRange,
    powerProfileIndex                           DellObjectRange,
    powerProfileSupportedProfiles               DellPowerProfileType,
    powerProfileSetting                         DellPowerProfileType,
    powerProfileCustomCPUMgmtCapabilities       DellCPUPowerPerformanceManagementType,
    powerProfileCustomCPUMgmtSetting            DellCPUPowerPerformanceManagementType,
    powerProfileCustomMemoryMgmtCapabilities    DellMemoryPowerPerformanceManagementType,
    powerProfileCustomMemoryMgmtSetting         DellMemoryPowerPerformanceManagementType,
    powerProfileCustomFanMgmtCapabilities       DellFanPowerPerformanceManagementType,
    powerProfileCustomFanMgmtSetting            DellFanPowerPerformanceManagementType
}

powerProfileTable                               OBJECT-TYPE
    SYNTAX      SEQUENCE OF PowerProfileTableEntry
    ACCESS      not-accessible
    STATUS      mandatory
    DESCRIPTION
"0600.0070 This object defines the Power Profile Table."
    ::= { powerGroup 70 }
powerProfileTableEntry                          OBJECT-TYPE
    SYNTAX      PowerProfileTableEntry
    ACCESS      not-accessible
    STATUS      mandatory
    DESCRIPTION
"0600.0070.0001 This object defines the Power Profile Table Entry."
    INDEX       { powerProfileChassisIndex,
                  powerProfileIndex }
    ::= { powerProfileTable 1 }

powerProfileChassisIndex                        OBJECT-TYPE
    SYNTAX      DellObjectRange
    ACCESS      read-only
    STATUS      mandatory
    DESCRIPTION
"0600.0070.0001.0001 This attribute defines the index (one based) of the
associated chassis."
    ::= { powerProfileTableEntry 1 }
powerProfileIndex                               OBJECT-TYPE
    SYNTAX      DellObjectRange
    ACCESS      read-only
    STATUS      mandatory
    DESCRIPTION
"0600.0060.0001.0002 This attribute defines the index (one based) of the
power profile information."
    ::= { powerProfileTableEntry 2 }
powerProfileSupportedProfiles                   OBJECT-TYPE
    SYNTAX      DellPowerProfileType
    ACCESS      read-only
    STATUS      mandatory
    DESCRIPTION
"0600.0070.0001.0003 This attribute defines the supported power profiles."
    ::= { powerProfileTableEntry 3 }
powerProfileSetting                             OBJECT-TYPE
    SYNTAX      DellPowerProfileType
    ACCESS      read-only
    STATUS      mandatory
    DESCRIPTION
"0600.0070.0001.0004 This attribute defines the power profile setting."
    ::= { powerProfileTableEntry 4 }
powerProfileCustomCPUMgmtCapabilities           OBJECT-TYPE
    SYNTAX      DellCPUPowerPerformanceManagementType
    ACCESS      read-only
    STATUS      mandatory
    DESCRIPTION
"0600.0070.0001.0005 This attribute defines the custom CPU power and
performance management capabilities that are available for the Custom
power profile."
    ::= { powerProfileTableEntry 5 }
powerProfileCustomCPUMgmtSetting                OBJECT-TYPE
    SYNTAX      DellCPUPowerPerformanceManagementType
    ACCESS      read-only
    STATUS      mandatory
    DESCRIPTION
"0600.0070.0001.0006 This attribute defines the custom CPU power and
performance management setting for the Custom power profile."
    ::= { powerProfileTableEntry 6 }
powerProfileCustomMemoryMgmtCapabilities        OBJECT-TYPE
    SYNTAX      DellMemoryPowerPerformanceManagementType
    ACCESS      read-only
    STATUS      mandatory
    DESCRIPTION
"0600.0070.0001.0007 This attribute defines the custom memory power and
performance management capabilities that are available for the Custom
power profile."
    ::= { powerProfileTableEntry 7 }
powerProfileCustomMemoryMgmtSetting             OBJECT-TYPE
    SYNTAX      DellMemoryPowerPerformanceManagementType
    ACCESS      read-only
    STATUS      mandatory
    DESCRIPTION
"0600.0070.0001.0008 This attribute defines the custom memory power and
performance management setting for the Custom power profile."
    ::= { powerProfileTableEntry 8 }
powerProfileCustomFanMgmtCapabilities           OBJECT-TYPE
    SYNTAX      DellFanPowerPerformanceManagementType
    ACCESS      read-only
    STATUS      mandatory
    DESCRIPTION
"0600.0070.0001.0009 This attribute defines the custom fan power and
performance management capabilities that are available for the Custom
power profile."
    ::= { powerProfileTableEntry 9 }
powerProfileCustomFanMgmtSetting                OBJECT-TYPE
    SYNTAX      DellFanPowerPerformanceManagementType
    ACCESS      read-only
    STATUS      mandatory
    DESCRIPTION
"0600.0070.0001.0010 This attribute defines the custom fan power and
performance management setting for the Custom power profile."
    ::= { powerProfileTableEntry 10 }


-------------------------------------------------------------------------------
-- Thermal Group
--
-- OID Format: 1.3.6.1.4.1.674.10892.1.700
-------------------------------------------------------------------------------


-------------------------------------------------------------------------------
-- Cooling Unit Table
--
-- OID Format: 1.3.6.1.4.1.674.10892.1.700.10.1.<a>.<i1>.<i2>
-------------------------------------------------------------------------------

CoolingUnitTableEntry                           ::= SEQUENCE {
    coolingUnitchassisIndex                     DellObjectRange,
    coolingUnitIndex                            DellObjectRange,
    coolingUnitStateCapabilties                 DellStateCapabilities,
    coolingUnitStateSettings                    DellStateSettings,
    coolingUnitRedundancyStatus                 DellStatusRedundancy,
    coolingDeviceCountForRedundancy             DellObjectRange,
    coolingUnitName                             DellString,
    coolingUnitStatus                           DellStatus
}

coolingUnitTable                                OBJECT-TYPE
    SYNTAX      SEQUENCE OF CoolingUnitTableEntry
    ACCESS      not-accessible
    STATUS      mandatory
    DESCRIPTION
"0700.0010 This object defines the Cooling Unit Table."
    ::= { thermalGroup 10 }
coolingUnitTableEntry                           OBJECT-TYPE
    SYNTAX      CoolingUnitTableEntry
    ACCESS      not-accessible
    STATUS      mandatory
    DESCRIPTION
"0700.0010.0001 This object defines the Cooling Unit Table Entry."
    INDEX       { coolingUnitchassisIndex,
                  coolingUnitIndex }
    ::= { coolingUnitTable 1 }

coolingUnitchassisIndex                         OBJECT-TYPE
    SYNTAX      DellObjectRange
    ACCESS      read-only
    STATUS      mandatory
    DESCRIPTION
"0700.0010.0001.0001 This attribute defines the index (one based) of the
assoicated chassis."
    ::= { coolingUnitTableEntry 1 }
coolingUnitIndex                                OBJECT-TYPE
    SYNTAX      DellObjectRange
    ACCESS      read-only
    STATUS      mandatory
    DESCRIPTION
"0700.0010.0001.0002 This attribute defines the index (one based) of the
cooling unit."
    ::= { coolingUnitTableEntry 2 }
coolingUnitStateCapabilties                     OBJECT-TYPE
    SYNTAX      DellStateCapabilities
    ACCESS      read-only
    STATUS      mandatory
    DESCRIPTION
"0700.0010.0001.0003 This attribute defines the state capabilities of the
cooling unit."
    ::= { coolingUnitTableEntry 3 }
coolingUnitStateSettings                        OBJECT-TYPE
    SYNTAX      DellStateSettings
    ACCESS      read-write
    STATUS      mandatory
    DESCRIPTION
"0700.0010.0001.0004 This attribute defines the state settings of the
cooling unit."
    ::= { coolingUnitTableEntry 4 }
coolingUnitRedundancyStatus                     OBJECT-TYPE
    SYNTAX      DellStatusRedundancy
    ACCESS      read-only
    STATUS      mandatory
    DESCRIPTION
"0700.0010.0001.0005 This attribute defines the redundancy status of the
cooling unit."
    ::= { coolingUnitTableEntry 5 }
coolingDeviceCountForRedundancy                 OBJECT-TYPE
    SYNTAX      DellObjectRange
    ACCESS      read-only
    STATUS      mandatory
    DESCRIPTION
"0700.0010.0001.0006 This attribute defines the total number of cooling devices
required for this cooling unit to have full redundancy."
    ::= { coolingUnitTableEntry 6 }
coolingUnitName                                 OBJECT-TYPE
    SYNTAX      DellString
    ACCESS      read-only
    STATUS      mandatory
    DESCRIPTION
"0700.0010.0001.0007 This attribute defines the name of the cooling unit."
    ::= { coolingUnitTableEntry 7 }
coolingUnitStatus                               OBJECT-TYPE
    SYNTAX      DellStatus
    ACCESS      read-only
    STATUS      mandatory
    DESCRIPTION
"0700.0010.0001.0008 This attribute defines the status of the cooling unit."
    ::= { coolingUnitTableEntry 8 }


-------------------------------------------------------------------------------
-- Cooling Device Table
--
-- OID Format: 1.3.6.1.4.1.674.10892.1.700.12.1.<a>.<i1>.<i2>
-------------------------------------------------------------------------------

DellCoolingDeviceType                           ::= INTEGER {
    coolingDeviceTypeIsOther(1),                -- type is other than following values
    coolingDeviceTypeIsUnknown(2),              -- type is unknown
    coolingDeviceTypeIsAFan(3),                 -- type is Fan
    coolingDeviceTypeIsABlower(4),              -- type is Centrifugal Blower
    coolingDeviceTypeIsAChipFan(5),             -- type is Fan on Integrated Circuit
    coolingDeviceTypeIsACabinetFan(6),          -- type is Cabinet Fan
    coolingDeviceTypeIsAPowerSupplyFan(7),      -- type is Power Supply Fan
    coolingDeviceTypeIsAHeatPipe(8),            -- type is Heat Pipe
    coolingDeviceTypeIsRefrigeration(9),        -- type is Integrated Refrigeration Unit
    coolingDeviceTypeIsActiveCooling(10),       -- type is Active Cooling Device
    coolingDeviceTypeIsPassiveCooling(11)       -- type is Passive Cooling Device
}
DellCoolingDeviceSubType                        ::= INTEGER {
    coolingDeviceSubTypeIsOther(1),             -- subtype is other than following values
    coolingDeviceSubTypeIsUnknown(2),           -- subtype is unknown
    coolingDeviceSubTypeIsAFanThatReadsInRPM(3),-- subtype is Fan that reads RPM
    coolingDeviceSubTypeIsAFanReadsONorOFF(4),  -- subtype is Fan that reads Off or On
    coolingDeviceSubTypeIsAPowerSupplyFanThatReadsinRPM(5),  -- subtype is Power Supply Fan that reads RPM
    coolingDeviceSubTypeIsAPowerSupplyFanThatReadsONorOFF(6),-- subtype is Power Supply Fan that reads Off or On
    coolingDeviceSubTypeIsDiscrete(16)          -- subtype is cooling device with discrete reading
}
DellCoolingDeviceDiscreteReading                ::= INTEGER {
    coolingDeviceIsGood(1),                     -- cooling device is Good
    coolingDeviceIsBad(2)                       -- cooling device is Bad
}

CoolingDeviceTableEntry                         ::= SEQUENCE {
    coolingDevicechassisIndex                   DellObjectRange,
    coolingDeviceIndex                          DellObjectRange,
    coolingDeviceStateCapabilities              DellStateCapabilities,
    coolingDeviceStateSettings                  DellStateSettings,
    coolingDeviceStatus                         DellStatusProbe,
    coolingDeviceReading                        DellSigned32BitRange,
    coolingDeviceType                           DellCoolingDeviceType,
    coolingDeviceLocationName                   DellString,
    coolingDeviceUpperNonRecoverableThreshold   DellSigned32BitRange,
    coolingDeviceUpperCriticalThreshold         DellSigned32BitRange,
    coolingDeviceUpperNonCriticalThreshold      DellSigned32BitRange,
    coolingDeviceLowerNonCriticalThreshold      DellSigned32BitRange,
    coolingDeviceLowerCriticalThreshold         DellSigned32BitRange,
    coolingDeviceLowerNonRecoverableThreshold   DellSigned32BitRange,
    coolingDevicecoolingUnitIndexReference      DellObjectRange,
    coolingDeviceSubType                        DellCoolingDeviceSubType,
    coolingDeviceProbeCapabilities              DellProbeCapabilities,
    coolingDeviceDiscreteReading                DellCoolingDeviceDiscreteReading
}

coolingDeviceTable                              OBJECT-TYPE
    SYNTAX      SEQUENCE OF CoolingDeviceTableEntry
    ACCESS      not-accessible
    STATUS      mandatory
    DESCRIPTION
"0700.0012 This object defines the Cooling Device Table."
    ::= {  thermalGroup 12 }
coolingDeviceTableEntry                         OBJECT-TYPE
    SYNTAX      CoolingDeviceTableEntry
    ACCESS      not-accessible
    STATUS      mandatory
    DESCRIPTION
"0700.0012.0001 This object defines the Cooling Device Table Entry."
    INDEX       { coolingDevicechassisIndex,
                  coolingDeviceIndex }
    ::= { coolingDeviceTable 1 }

coolingDevicechassisIndex                       OBJECT-TYPE
    SYNTAX      DellObjectRange
    ACCESS      read-only
    STATUS      mandatory
    DESCRIPTION
"0700.0012.0001.0001 This attribute defines the index (one based) of the
associated chassis."
    ::= { coolingDeviceTableEntry 1 }
coolingDeviceIndex                              OBJECT-TYPE
    SYNTAX      DellObjectRange
    ACCESS      read-only
    STATUS      mandatory
    DESCRIPTION
"0700.0012.0001.0002 This attribute defines the index (one based) of the
cooling device."
    ::= { coolingDeviceTableEntry 2 }
coolingDeviceStateCapabilities                  OBJECT-TYPE
    SYNTAX      DellStateCapabilities
    ACCESS      read-only
    STATUS      mandatory
    DESCRIPTION
"0700.0012.0001.0003 This attribute defines the state capabilities of the
cooling device."
    ::= { coolingDeviceTableEntry 3 }
coolingDeviceStateSettings                      OBJECT-TYPE
    SYNTAX      DellStateSettings
    ACCESS      read-write
    STATUS      mandatory
    DESCRIPTION
"0700.0012.0001.0004 This attribute defines the state settings of the
cooling device."
    ::= { coolingDeviceTableEntry 4 }
coolingDeviceStatus                             OBJECT-TYPE
    SYNTAX      DellStatusProbe
    ACCESS      read-only
    STATUS      mandatory
    DESCRIPTION
"0700.0012.0001.0005 This attribute defines the probe status of the
cooling device."
    ::= { coolingDeviceTableEntry 5 }
coolingDeviceReading                            OBJECT-TYPE
    SYNTAX      DellSigned32BitRange
    ACCESS      read-only
    STATUS      mandatory
    DESCRIPTION
"0700.0012.0001.0006 This attribute defines the reading for a cooling device
of subtype other than coolingDeviceSubTypeIsDiscrete.  When the value
for coolingDeviceSubType is other than coolingDeviceSubTypeIsDiscrete, the
value returned for this attribute is the speed in RPM or the OFF/ON value
of the cooling device.  When the value for coolingDeviceSubType is
coolingDeviceSubTypeIsDiscrete, a value is not returned for this attribute."
    ::= { coolingDeviceTableEntry 6 }
coolingDeviceType                               OBJECT-TYPE
    SYNTAX      DellCoolingDeviceType
    ACCESS      read-only
    STATUS      mandatory
    DESCRIPTION
"0700.0012.0001.0007 This attribute defines the type of the cooling device."
    ::= { coolingDeviceTableEntry 7 }
coolingDeviceLocationName                       OBJECT-TYPE
    SYNTAX      DellString
    ACCESS      read-only
    STATUS      mandatory
    DESCRIPTION
"0700.0012.0001.0008 This attribute defines the location name of the
cooling device."
    ::= { coolingDeviceTableEntry 8 }
coolingDeviceUpperNonRecoverableThreshold       OBJECT-TYPE
    SYNTAX      DellSigned32BitRange
    ACCESS      read-only
    STATUS      mandatory
    DESCRIPTION
"0700.0012.0001.0009 This attribute defines the upper nonrecoverable threshold
of the cooling device.  The value is an integer representing fan speed
in revolutions per minute (RPM).  It is not applicable to OFF/ON type
cooling devices or non-cooling device types."
    ::= { coolingDeviceTableEntry 9 }
coolingDeviceUpperCriticalThreshold             OBJECT-TYPE
    SYNTAX      DellSigned32BitRange
    ACCESS      read-only
    STATUS      mandatory
    DESCRIPTION
"0700.0012.0001.0010 This attribute defines the upper critical threshold
of the cooling device.  The value is an integer representing fan speed
in revolutions per minute (RPM).  It is not applicable to OFF/ON type
cooling devices or non-cooling device types."
    ::= { coolingDeviceTableEntry 10 }
coolingDeviceUpperNonCriticalThreshold          OBJECT-TYPE
    SYNTAX      DellSigned32BitRange
    ACCESS      read-write
    STATUS      mandatory
    DESCRIPTION
"0700.0012.0001.0011 This attribute defines the upper noncritical threshold
of the cooling device.  The value is an integer representing fan speed
in revolutions per minute (RPM).  It is not applicable to OFF/ON type
cooling devices or non-cooling device types."
    ::= { coolingDeviceTableEntry 11 }
coolingDeviceLowerNonCriticalThreshold          OBJECT-TYPE
    SYNTAX      DellSigned32BitRange
    ACCESS      read-write
    STATUS      mandatory
    DESCRIPTION
"0700.0012.0001.0012 This attribute defines the lower noncritical threshold
of the cooling device.  The value is an integer representing fan speed
in revolutions per minute (RPM).  It is not applicable to OFF/ON type
cooling devices or non-cooling device types."
    ::= { coolingDeviceTableEntry 12 }
coolingDeviceLowerCriticalThreshold             OBJECT-TYPE
    SYNTAX      DellSigned32BitRange
    ACCESS      read-only
    STATUS      mandatory
    DESCRIPTION
"0700.0012.0001.0013 This attribute defines the lower critical threshold
of the cooling device.  The value is an integer representing fan speed
in revolutions per minute (RPM).  It is not applicable to OFF/ON type
cooling devices or non-cooling device types."
    ::= { coolingDeviceTableEntry 13 }
coolingDeviceLowerNonRecoverableThreshold       OBJECT-TYPE
    SYNTAX      DellSigned32BitRange
    ACCESS      read-only
    STATUS      mandatory
    DESCRIPTION
"0700.0012.0001.0014 This attribute defines the lower nonrecoverable threshold
of the cooling device.  The value is an integer representing fan speed
in revolutions per minute (RPM).  It is not applicable to OFF/ON type
cooling devices or non-cooling device types."
    ::= { coolingDeviceTableEntry 14 }
coolingDevicecoolingUnitIndexReference          OBJECT-TYPE
    SYNTAX      DellObjectRange
    ACCESS      read-only
    STATUS      mandatory
    DESCRIPTION
"0700.0012.0001.0015 This attribute defines the index to the associated
cooling unit."
    ::= { coolingDeviceTableEntry 15 }
coolingDeviceSubType                            OBJECT-TYPE
    SYNTAX      DellCoolingDeviceSubType
    ACCESS      read-only
    STATUS      mandatory
    DESCRIPTION
"0700.0012.0001.0016 This attribute defines the subtype of the cooling device."
    ::= { coolingDeviceTableEntry 16 }
coolingDeviceProbeCapabilities                  OBJECT-TYPE
    SYNTAX      DellProbeCapabilities
    ACCESS      read-only
    STATUS      mandatory
    DESCRIPTION
"0700.0012.0001.0017 This attribute defines the probe capabilities of the
cooling device."
    ::= { coolingDeviceTableEntry 17 }
coolingDeviceDiscreteReading                    OBJECT-TYPE
    SYNTAX      DellCoolingDeviceDiscreteReading
    ACCESS      read-only
    STATUS      mandatory
    DESCRIPTION
"0700.0012.0001.0018 This attribute defines the reading for a cooling device
of type coolingDeviceSubTypeIsDiscrete.  When the value for
coolingDeviceSubType is other than coolingDeviceSubTypeIsDiscrete, a value
is not returned for this attribute.  When the value for coolingDeviceSubType
is coolingDeviceSubTypeIsDiscrete, the value returned for this attribute
is the discrete reading for the cooling device."
    ::= { coolingDeviceTableEntry 18 }


-------------------------------------------------------------------------------
-- Temperature Probe Table
--
-- OID Format: 1.3.6.1.4.1.674.10892.1.700.20.1.<a>.<i1>.<i2>
-------------------------------------------------------------------------------

DellTemperatureProbeType                        ::= INTEGER {
    temperatureProbeTypeIsOther(1),             -- type is other than following values
    temperatureProbeTypeIsUnknown(2),           -- type is unknown
    temperatureProbeTypeIsAmbientESM(3),        -- type is Ambient Embedded Systems Management temperature probe
    temperatureProbeTypeIsDiscrete(16)          -- type is temperature probe with discrete reading
}
DellTemperatureDiscreteReading                  ::= INTEGER {
    temperatureIsGood(1),                       -- temperature reading is Good
    temperatureIsBad(2)                         -- temperature reading is Bad
}

TemperatureProbeTableEntry                      ::= SEQUENCE {
    temperatureProbechassisIndex                DellObjectRange,
    temperatureProbeIndex                       DellObjectRange,
    temperatureProbeStateCapabilities           DellStateCapabilities,
    temperatureProbeStateSettings               DellStateSettings,
    temperatureProbeStatus                      DellStatusProbe,
    temperatureProbeReading                     DellSigned32BitRange,
    temperatureProbeType                        DellTemperatureProbeType,
    temperatureProbeLocationName                DellString,
    temperatureProbeUpperNonRecoverableThreshold DellSigned32BitRange,
    temperatureProbeUpperCriticalThreshold      DellSigned32BitRange,
    temperatureProbeUpperNonCriticalThreshold   DellSigned32BitRange,
    temperatureProbeLowerNonCriticalThreshold   DellSigned32BitRange,
    temperatureProbeLowerCriticalThreshold      DellSigned32BitRange,
    temperatureProbeLowerNonRecoverableThreshold DellSigned32BitRange,
    temperatureProbeProbeCapabilities           DellProbeCapabilities,
    temperatureProbeDiscreteReading             DellTemperatureDiscreteReading
}

temperatureProbeTable                           OBJECT-TYPE
    SYNTAX      SEQUENCE OF TemperatureProbeTableEntry
    ACCESS      not-accessible
    STATUS      mandatory
    DESCRIPTION
"0700.0020 This object defines the Temperature Probe Table."
    ::= { thermalGroup 20 }
temperatureProbeTableEntry                      OBJECT-TYPE
    SYNTAX      TemperatureProbeTableEntry
    ACCESS      not-accessible
    STATUS      mandatory
    DESCRIPTION
"0700.0020.0001 This object defines the Temperature Probe Table Entry."
    INDEX       { temperatureProbechassisIndex,
                  temperatureProbeIndex }
    ::= { temperatureProbeTable 1 }

temperatureProbechassisIndex                    OBJECT-TYPE
    SYNTAX      DellObjectRange
    ACCESS      read-only
    STATUS      mandatory
    DESCRIPTION
"0700.0020.0001.0001 This attribute defines the index (one based) of the
associated chassis."
    ::= { temperatureProbeTableEntry 1 }
temperatureProbeIndex                           OBJECT-TYPE
    SYNTAX      DellObjectRange
    ACCESS      read-only
    STATUS      mandatory
    DESCRIPTION
"0700.0020.0001.0002 This attribute defines the index (one based) of the
temperature probe."
    ::= { temperatureProbeTableEntry 2 }
temperatureProbeStateCapabilities               OBJECT-TYPE
    SYNTAX      DellStateCapabilities
    ACCESS      read-only
    STATUS      mandatory
    DESCRIPTION
"0700.0020.0001.0003 This attribute defines the state capabilities of the
temperature probe."
    ::= { temperatureProbeTableEntry 3 }
temperatureProbeStateSettings                   OBJECT-TYPE
    SYNTAX      DellStateSettings
    ACCESS      read-write
    STATUS      mandatory
    DESCRIPTION
"0700.0020.0001.0004 This attribute defines the state settings of the
temperature probe."
    ::= { temperatureProbeTableEntry 4 }
temperatureProbeStatus                          OBJECT-TYPE
    SYNTAX      DellStatusProbe
    ACCESS      read-only
    STATUS      mandatory
    DESCRIPTION
"0700.0020.0001.0005 This attribute defines the probe status of the
temperature probe."
    ::= { temperatureProbeTableEntry 5 }
temperatureProbeReading                         OBJECT-TYPE
    SYNTAX      DellSigned32BitRange
    ACCESS      read-only
    STATUS      mandatory
    DESCRIPTION
"0700.0020.0001.0006 This attribute defines the reading for a temperature
probe of type other than temperatureProbeTypeIsDiscrete.  When the value
for temperatureProbeType is other than temperatureProbeTypeIsDiscrete,
the value returned for this attribute is the temperature that the probe
is reading in tenths of degrees Centigrade.  When the value for
temperatureProbeType is temperatureProbeTypeIsDiscrete, a value is not
returned for this attribute."
    ::= { temperatureProbeTableEntry 6 }
temperatureProbeType                            OBJECT-TYPE
    SYNTAX      DellTemperatureProbeType
    ACCESS      read-only
    STATUS      mandatory
    DESCRIPTION
"0700.0020.0001.0007 This attribute defines the type of the temperature probe."
    ::= { temperatureProbeTableEntry 7 }
temperatureProbeLocationName                    OBJECT-TYPE
    SYNTAX      DellString
    ACCESS      read-only
    STATUS      mandatory
    DESCRIPTION
"0700.0020.0001.0008 This attribute defines the location name of the
temperature probe."
    ::= { temperatureProbeTableEntry 8 }
temperatureProbeUpperNonRecoverableThreshold    OBJECT-TYPE
    SYNTAX      DellSigned32BitRange
    ACCESS      read-only
    STATUS      mandatory
    DESCRIPTION
"0700.0020.0001.0009 This attribute defines the upper nonrecoverable threshold
of the temperature probe.  The value is an integer representing the temperature
of the threshold in tenths of degrees Centigrade."
    ::= { temperatureProbeTableEntry 9 }
temperatureProbeUpperCriticalThreshold          OBJECT-TYPE
    SYNTAX      DellSigned32BitRange
    ACCESS      read-only
    STATUS      mandatory
    DESCRIPTION
"0700.0020.0001.0010 This attribute defines the upper critical threshold
of the temperature probe.  The value is an integer representing the temperature
of the threshold in tenths of degrees Centigrade."
    ::= { temperatureProbeTableEntry 10 }
temperatureProbeUpperNonCriticalThreshold       OBJECT-TYPE
    SYNTAX      DellSigned32BitRange
    ACCESS      read-write
    STATUS      mandatory
    DESCRIPTION
"0700.0020.0001.0011 This attribute defines the upper noncritical threshold
of the temperature probe.  The value is an integer representing the temperature
of the threshold in tenths of degrees Centigrade."
    ::= { temperatureProbeTableEntry 11 }
temperatureProbeLowerNonCriticalThreshold       OBJECT-TYPE
    SYNTAX      DellSigned32BitRange
    ACCESS      read-write
    STATUS      mandatory
    DESCRIPTION
"0700.0020.0001.0012 This attribute defines the lower noncritical threshold
of the temperature probe.  The value is an integer representing the temperature
of the threshold in tenths of degrees Centigrade."
    ::= { temperatureProbeTableEntry 12 }
temperatureProbeLowerCriticalThreshold          OBJECT-TYPE
    SYNTAX      DellSigned32BitRange
    ACCESS      read-only
    STATUS      mandatory
    DESCRIPTION
"0700.0020.0001.0013 This attribute defines the lower critical threshold
of the temperature probe.  The value is an integer representing the temperature
of the threshold in tenths of degrees Centigrade."
    ::= { temperatureProbeTableEntry 13 }
temperatureProbeLowerNonRecoverableThreshold    OBJECT-TYPE
    SYNTAX      DellSigned32BitRange
    ACCESS      read-only
    STATUS      mandatory
    DESCRIPTION
"0700.0020.0001.0014 This attribute defines the lower nonrecoverable threshold
of the temperature probe.  The value is an integer representing the temperature
of the threshold in tenths of degrees Centigrade."
    ::= { temperatureProbeTableEntry 14 }
temperatureProbeProbeCapabilities               OBJECT-TYPE
    SYNTAX      DellProbeCapabilities
    ACCESS      read-only
    STATUS      mandatory
    DESCRIPTION
"0700.0020.0001.0015 This attribute defines the probe capabilities of the
temperature probe."
    ::= { temperatureProbeTableEntry 15 }
temperatureProbeDiscreteReading                 OBJECT-TYPE
    SYNTAX      DellTemperatureDiscreteReading
    ACCESS      read-only
    STATUS      mandatory
    DESCRIPTION
"0700.0020.0001.0016 This attribute defines the reading for a temperature
probe of type temperatureProbeTypeIsDiscrete.  When the value for
temperatureProbeType is other than temperatureProbeTypeIsDiscrete, a value
is not returned for this attribute.  When the value for temperatureProbeType
is temperatureProbeTypeIsDiscrete, the value returned for this attribute
is the discrete reading for the probe."
    ::= { temperatureProbeTableEntry 16 }


-------------------------------------------------------------------------------
-- User Security Group
--
-- OID Format: 1.3.6.1.4.1.674.10892.1.800
-------------------------------------------------------------------------------


-------------------------------------------------------------------------------
-- User Security Table
--
-- OID Format: 1.3.6.1.4.1.674.10892.1.800.10.1.<a>.<i1>.<i2>
-------------------------------------------------------------------------------

UserSecurityTableEntry                          ::= SEQUENCE {
    userSecuritychassisIndex                    DellObjectRange,
    userSecurityIndex                           DellObjectRange,
    userSecurityUserName                        DellSecurityString,
    userSecurityControlName                     DellSecurityString,
    userSecurityRequestName                     DellSecurityString
}

userSecurityTable                               OBJECT-TYPE
    SYNTAX      SEQUENCE OF UserSecurityTableEntry
    ACCESS      not-accessible
    STATUS      mandatory
    DESCRIPTION
"0800.0010 This object defines the User Security Table."
    ::= { userSecurityGroup 10 }
userSecurityTableEntry                          OBJECT-TYPE
    SYNTAX      UserSecurityTableEntry
    ACCESS      not-accessible
    STATUS      mandatory
    DESCRIPTION
"0800.0010.0001 This object defines the User Security Table Entry."
    INDEX       { userSecuritychassisIndex,
                  userSecurityIndex }
    ::= { userSecurityTable 1 }

userSecuritychassisIndex                        OBJECT-TYPE
    SYNTAX      DellObjectRange
    ACCESS      read-only
    STATUS      mandatory
    DESCRIPTION
"0800.0010.0001.0001 This attribute defines the index (one based) of the
assoicated chassis."
    ::= { userSecurityTableEntry 1 }
userSecurityIndex                               OBJECT-TYPE
    SYNTAX      DellObjectRange
    ACCESS      read-only
    STATUS      mandatory
    DESCRIPTION
"0800.0010.0001.0002 This attribute defines the index (one based) of the
user."
    ::= { userSecurityTableEntry 2 }
userSecurityUserName                            OBJECT-TYPE
    SYNTAX      DellSecurityString
    ACCESS      read-only
    STATUS      mandatory
    DESCRIPTION
"0800.0010.0001.0003 This attribute defines the name of the user
that is authorized to perform Set operations on this system."
    ::= { userSecurityTableEntry 3 }
userSecurityControlName                         OBJECT-TYPE
    SYNTAX      DellSecurityString
    ACCESS      read-write
    STATUS      mandatory
    DESCRIPTION
"0800.0010.0001.0004 This attribute defines the control string
that is used for managing users in this table."
    ::= { userSecurityTableEntry 4 }
userSecurityRequestName                         OBJECT-TYPE
    SYNTAX      DellSecurityString
    ACCESS      read-write
    STATUS      mandatory
    DESCRIPTION
"0800.0010.0001.0005 This attribute defines the request string
that is used for Set requests on this system."
    ::= { userSecurityTableEntry 5 }


-------------------------------------------------------------------------------
-- Remote Flash BIOS Group
--
-- OID Format: 1.3.6.1.4.1.674.10892.1.900
-------------------------------------------------------------------------------


-------------------------------------------------------------------------------
-- Remote Flash BIOS Table
--
-- OID Format: 1.3.6.1.4.1.674.10892.1.900.10.1.<a>.<i1>.<i2>
-------------------------------------------------------------------------------

DellRemoteFlashBIOSStateCapabilitiesUnique      ::= INTEGER {
    -- If 0 (zero), there are no remote flash BIOS state capabilities
    unknown(1),                                 -- state capabilities are unknown
    enableCapable(2),                           -- remote flash BIOS can be enabled (online) or be disabled (offline)
    notReadyCapable(4),                         -- remote flash BIOS can be not ready
    cancelCapable(8),                           -- remote flash BIOS can be canceled
    enableAndCancelCapable(10)                  -- remote flash BIOS can be enabled and canceled
}
DellRemoteFlashBIOSStateSettingsUnique          ::= INTEGER {
    -- If 0 (zero), there are no remote flash BIOS state settings
    unknown(1),                                 -- state settings are unknown
    enabled(2),                                 -- remote flash BIOS is enabled
    notReady(4),                                -- remote flash BIOS is not ready
    canceled(8),                                -- remote flash BIOS is canceled
    pending(16),                                -- remote flash BIOS is pending
    other(32)                                   -- state settings are other than above
}
DellRemoteFlashBIOSCompletionCode               ::= INTEGER {
    completionCodeIsOther(1),                   -- code is other than following values
    completionCodeIsUnknown(2),                 -- code is unknown
    completionCodeIsOK(3),                      -- code is completed successfully
    completionCodeIsBadImage(4),                -- code is bad flash BIOS image
    completionCodeIsNoFileAccess(5),            -- code is flash BIOS image could not be accessed
    completionCodeIsNotReady(6),                -- code is flash BIOS memory not ready
    completionCodeIsDisabled(7),                -- code is flash BIOS is currently disabled
    completionCodeIsNoBattery(8),               -- code is battery must be installed
    completionCodeIsNoChargedBattery(9),        -- code is fully charged battery must be installed
    completionCodeIsNoExternalPower(10),        -- code is external power adapter must be connected
    completionCodeIsNo12VoltSet(11),            -- code is that 12 volts could not be set
    completionCodeIsNo12VoltRemoval(12),        -- code is that 12 volts could not be removed
    completionCodeIsFlashMemoryFailed(13),      -- code is flash memory failure occured
    completionCodeIsGeneralFailure(14),         -- code is general failure occurred
    completionCodeIsDataMiscompare(15),         -- code is data miscompare error occurred
    completionCodeIsNoImageFound(16),           -- code is flash BIOS image could not be found in memory
    completionCodeIsNoUpdatePerformed(17)       -- code is no update operation has been performed
}

RemoteFlashBIOSTableEntry                       ::= SEQUENCE {
    remoteFlashBIOSchassisIndex                 DellObjectRange,
    remoteFlashBIOSIndex                        DellObjectRange,
    remoteFlashBIOSStateCapabilitiesUnique      DellRemoteFlashBIOSStateCapabilitiesUnique,
    remoteFlashBIOSStateSettingsUnique          DellRemoteFlashBIOSStateSettingsUnique,
    remoteFlashBIOSStatus                       DellStatus,
    remoteFlashBIOSLastBIOSDateName             DellDateName,
    remoteFlashBIOSCompletionCode               DellRemoteFlashBIOSCompletionCode,
    remoteFlashBIOSMinimumContiguousMemory      DellUnsigned32BitRange
}

remoteFlashBIOSTable                            OBJECT-TYPE
    SYNTAX      SEQUENCE OF RemoteFlashBIOSTableEntry
    ACCESS      not-accessible
    STATUS      mandatory
    DESCRIPTION
"0900.0010 This object defines the Remote Flash BIOS Table."
    ::= { remoteFlashBIOSGroup 10 }
remoteFlashBIOSTableEntry                       OBJECT-TYPE
    SYNTAX      RemoteFlashBIOSTableEntry
    ACCESS      not-accessible
    STATUS      mandatory
    DESCRIPTION
"0900.0010.0001 This object defines the Remote Flash BIOS Table Entry."
    INDEX       { remoteFlashBIOSchassisIndex,
                  remoteFlashBIOSIndex }
    ::= { remoteFlashBIOSTable 1 }

remoteFlashBIOSchassisIndex                     OBJECT-TYPE
    SYNTAX      DellObjectRange
    ACCESS      read-only
    STATUS      mandatory
    DESCRIPTION
"0900.0010.0001.0001 This attribute defines the index (one based) of the
associated chassis."
    ::= { remoteFlashBIOSTableEntry 1 }
remoteFlashBIOSIndex                            OBJECT-TYPE
    SYNTAX      DellObjectRange
    ACCESS      read-only
    STATUS      mandatory
    DESCRIPTION
"0900.0010.0001.0002 This attribute defines the index (one based) of the
remote flash BIOS function."
    ::= { remoteFlashBIOSTableEntry 2 }
remoteFlashBIOSStateCapabilitiesUnique          OBJECT-TYPE
    SYNTAX      DellRemoteFlashBIOSStateCapabilitiesUnique
    ACCESS      read-only
    STATUS      mandatory
    DESCRIPTION
"0900.0010.0001.0003 This attribute defines the state capabilities of the
remote flash BIOS function."
    ::= { remoteFlashBIOSTableEntry 3 }
remoteFlashBIOSStateSettingsUnique              OBJECT-TYPE
    SYNTAX      DellRemoteFlashBIOSStateSettingsUnique
    ACCESS      read-write
    STATUS      mandatory
    DESCRIPTION
"0900.0010.0001.0004 This attribute defines the state settings of the
remote flash BIOS function."
    ::= { remoteFlashBIOSTableEntry 4 }
remoteFlashBIOSStatus                           OBJECT-TYPE
    SYNTAX      DellStatus
    ACCESS      read-only
    STATUS      mandatory
    DESCRIPTION
"0900.0010.0001.0005 This attribute defines the status of the
remote flash BIOS function."
    ::= { remoteFlashBIOSTableEntry 5 }
remoteFlashBIOSLastBIOSDateName                 OBJECT-TYPE
    SYNTAX      DellDateName
    ACCESS      read-only
    STATUS      mandatory
    DESCRIPTION
"0900.0010.0001.0006 This attribute defines the date of last BIOS update.
Dates are defined in the ASCII format:
      yyyyMMddhhmmss.uuuuuu+fff or yyyyMMddhhmmss.uuuuuu-fff
where yyyy is the year, MM is the month, dd is the day, hh are the hours,
mm are the minutes and ss are the seconds.
uuuuuu is the number of microseconds, and +fff or -fff is the offset from
UTC in minutes."
    ::= { remoteFlashBIOSTableEntry 6 }
remoteFlashBIOSCompletionCode                   OBJECT-TYPE
    SYNTAX      DellRemoteFlashBIOSCompletionCode
    ACCESS      read-only
    STATUS      mandatory
    DESCRIPTION
"0900.0010.0001.0007 This attribute defines the completion code of the
last BIOS update."
    ::= { remoteFlashBIOSTableEntry 7 }
remoteFlashBIOSMinimumContiguousMemory          OBJECT-TYPE
    SYNTAX      DellUnsigned32BitRange
    ACCESS      read-only
    STATUS      mandatory
    DESCRIPTION
"0900.0010.0001.0008 This attribute defines the minimum size of contiguous
memory required for the remote flash BIOS function in KBbytes."
    ::= { remoteFlashBIOSTableEntry 8 }


-------------------------------------------------------------------------------
-- Port Group
--
-- OID Format: 1.3.6.1.4.1.674.10892.1.1000
-------------------------------------------------------------------------------


DellGenericPortConnectorType                    ::= INTEGER {
    portConnectorTypeIsOther(1),                -- type is other than following values
    portConnectorTypeIsNone(2),                 -- type is no port connector
    portConnectorTypeIsCentronics(3),           -- type is Centronics, IEEE1284-B Receptical
    portConnectorTypeIsMiniCentronics(4),       -- type is MiniCentronics, IEEE1284-C Receptical
    portConnectorTypeIsProprietary(5),          -- type is Proprietary
    portConnectorTypeIsDB25Male(6),             -- type is Male DB-25, IEEE1284-A Plug
    portConnectorTypeIsDB25Female(7),           -- type is Female DB-25, IEEE1284-A Receptical
    portConnectorTypeIsDB15Male(8),             -- type is Male DB-15
    portConnectorTypeIsDB15Female(9),           -- type is Female DB-15
    portConnectorTypeIsDB9Male(10),             -- type is Male DB-9
    portConnectorTypeIsDB9Female(11),           -- type is Female DB-9
    portConnectorTypeIsRJ11(12),                -- type is RJ-11
    portConnectorTypeIsRJ45(13),                -- type is RJ-45
    portConnectorTypeIsMiniSCSI50Pin(14),       -- type is 50 pin MiniSCSI
    portConnectorTypeIsMiniDIN(15),             -- type is Mini DIN
    portConnectorTypeIsMicroDIN(16),            -- type is Micro DIN
    portConnectorTypeIsPS2(17),                 -- type is PS/2
    portConnectorTypeIsInfrared(18),            -- type is Infrared
    portConnectorTypeIsHPHIL(19),               -- type is HP-HIL
    portConnectorTypeIsAccessBussUSB(20),       -- type is Access Bus USB
    portConnectorTypeISSASCSI(21),              -- type is SSA SCSI
    portConnectorTypeIsCirdin8Male(22),         -- type is Male Circular DIN-8
    portConnectorTypeIsCirdin8Female(23),       -- type is Female Circular DIN-8
    portConnectorTypeIsIDE(24),                 -- type is IDE
    portConnectorTypeIsFloppy(25),              -- type is Floppy
    portConnectorTypeIsDIN9Pin(26),             -- type is 9-pin Dual Inline
    portConnectorTypeIsDIN25Pin(27),            -- type is 25-pin Dual Inline
    portConnectorTypeIsDIN50Pin(28),            -- type is 50-pin Dual Inline
    portConnectorTypeIsDIN68Pin(29),            -- type is 68-pin Dual Inline
    portConnectorTypeIsCDROMLineOut(30),        -- type is CDROM Line Output
    portConnectorTypeIsMiniCentronics14(31),    -- type is MiniCentronics 14
    portConnectorTypeIsMiniCentronics26(32),    -- type is MiniCentronics 26
    portConnectorTypeIsMiniJack(33),            -- type is Minijack, headphones
    portConnectorTypeIsBNC(34),                 -- type is BNC
    portConnectorTypeIs1394(35),                -- type is 1394, firewire
    portConnectorTypeIsPC98(36),                -- type is PC-98
    portConnectorTypeIsPC98Hireso(37),          -- type is PC-98 Hireso
    portConnectorTypeIsPCH98(38),               -- type is PCH98
    portConnectorTypeIsPC98Note(39),            -- type is PC-98 Note
    portConnectorTypeIsPC98Full(40)             -- type is PC-98 Full
}
DellPortSecurityState                           ::= INTEGER {
    other(1),                                   -- security state is other than following values
    unknown(2),                                 -- security state is unknown
    none(3),                                    -- security state is no security
    externalIsDisabled(4),                      -- security state is external interface is disabled
    externalIsEnabled(5),                       -- security state is external interface is enabled
    bootByPass(6)                               -- security state is boot bypass
}


-------------------------------------------------------------------------------
-- Pointing Port Table
--
-- OID Format: 1.3.6.1.4.1.674.10892.1.1000.10.1.<a>.<i1>.<i2>
-------------------------------------------------------------------------------

DellPointingPortConnectorType                   ::= INTEGER {
    connectorPortTypeIsOther(1),                -- type is other than following values
    connectorPortTypeIsUnknown(2),              -- type is unknown
    connectorPortTypeIsSerial(3),               -- type is Serial
    connectorPortTypeIsPS2(4),                  -- type is PS/2
    connectorPortTypeIsInfrared(5),             -- type is Infrared
    connectorPortTypeIsHPHIL(6),                -- type is HP-HIL
    connectorPortTypeIsBusMouse(7),             -- type is Bus Mouse
    connectorPortTypeIsADB(8),                  -- type is ADB
    connectorPortTypeIsDB9(9),                  -- type is DB-9
    connectorPortTypeIsMicroDIN(10),            -- type is Micro DIN
    connectorPortTypeIsAccessBusUSB(11),        -- type is Access Bus USB
    connectorPortTypeIsPC98(12)                 -- type is PC-98
}

PointingPortTableEntry                          ::= SEQUENCE {
    pointingPortchassisIndex                    DellObjectRange,
    pointingPortIndex                           DellObjectRange,
    pointingPortStateCapabilities               DellStateCapabilities,
    pointingPortStateSettings                   DellStateSettings,
    pointingPortStatus                          DellStatus,
    pointingPortSecurityState                   DellPortSecurityState,
    pointingPortConnectorType                   DellPointingPortConnectorType,
    pointingPortName                            DellString,
    pointingPortBIOSConnectorType               DellGenericPortConnectorType
}

pointingPortTable                               OBJECT-TYPE
    SYNTAX      SEQUENCE OF PointingPortTableEntry
    ACCESS      not-accessible
    STATUS      mandatory
    DESCRIPTION
"1000.0010 This object defines the Pointing Port Table."
    ::= { portGroup 10 }
pointingPortTableEntry                          OBJECT-TYPE
    SYNTAX      PointingPortTableEntry
    ACCESS      not-accessible
    STATUS      mandatory
    DESCRIPTION
"1000.0010.0001 This object defines the Pointing Port Table Entry."
    INDEX       { pointingPortchassisIndex,
                  pointingPortIndex }
    ::= { pointingPortTable 1 }

pointingPortchassisIndex                        OBJECT-TYPE
    SYNTAX      DellObjectRange
    ACCESS      read-only
    STATUS      mandatory
    DESCRIPTION
"1000.0010.0001.0001 This attribute defines the index (one based) of the
associated chassis."
    ::= { pointingPortTableEntry 1 }
pointingPortIndex                               OBJECT-TYPE
    SYNTAX      DellObjectRange
    ACCESS      read-only
    STATUS      mandatory
    DESCRIPTION
"1000.0010.0001.0002 This attribute defines the index (one based) of the
pointing port."
    ::= { pointingPortTableEntry 2 }
pointingPortStateCapabilities                   OBJECT-TYPE
    SYNTAX      DellStateCapabilities
    ACCESS      read-only
    STATUS      mandatory
    DESCRIPTION
"1000.0010.0001.0003 This attribute defines the state capabilities of the
pointing port."
    ::= { pointingPortTableEntry 3 }
pointingPortStateSettings                       OBJECT-TYPE
    SYNTAX      DellStateSettings
    ACCESS      read-write
    STATUS      mandatory
    DESCRIPTION
"1000.0010.0001.0004 This attribute defines the state settings of the
pointing port."
    ::= { pointingPortTableEntry 4 }
pointingPortStatus                              OBJECT-TYPE
    SYNTAX      DellStatus
    ACCESS      read-only
    STATUS      mandatory
    DESCRIPTION
"1000.0010.0001.0005 This attribute defines the status of the
pointing port."
    ::= { pointingPortTableEntry 5 }
pointingPortSecurityState                       OBJECT-TYPE
    SYNTAX      DellPortSecurityState
    ACCESS      read-only
    STATUS      mandatory
    DESCRIPTION
"1000.0010.0001.0006 This attribute defines the security state of the
pointing port."
    ::= { pointingPortTableEntry 6 }
pointingPortConnectorType                       OBJECT-TYPE
    SYNTAX      DellPointingPortConnectorType
    ACCESS      read-only
    STATUS      mandatory
    DESCRIPTION
"1000.0010.0001.0007 This attribute defines the connector type of the
pointing port."
    ::= { pointingPortTableEntry 7 }
pointingPortName                                OBJECT-TYPE
    SYNTAX      DellString
    ACCESS      read-only
    STATUS      mandatory
    DESCRIPTION
"1000.0010.0001.0008 This attribute defines name of the pointing port."
    ::= { pointingPortTableEntry 8 }
pointingPortBIOSConnectorType                   OBJECT-TYPE
    SYNTAX      DellGenericPortConnectorType
    ACCESS      read-only
    STATUS      mandatory
    DESCRIPTION
"1000.0010.0001.0009 This attribute defines the BIOS connector type of the
pointing port."
    ::= { pointingPortTableEntry 9 }


-------------------------------------------------------------------------------
-- Keyboard Port Table
--
-- OID Format: 1.3.6.1.4.1.674.10892.1.1000.20.1.<a>.<i1>.<i2>
-------------------------------------------------------------------------------

DellKeyboardPortConnectorType                   ::= INTEGER {
    connectorPortTypeIsOther(1),                -- type is other than following values
    connectorPortTypeIsUnknown(2),              -- type is unknown
    connectorPortTypeIsMiniDIN(3),              -- type is Mini DIN
    connectorPortTypeIsMicroDIN(4),             -- type is Micro DIN
    connectorPortTypeIsPS2(5),                  -- type is PS/2
    connectorPortTypeIsInfrared(6),             -- type is Infrared
    connectorPortTypeIsHPHIL(7),                -- type is HP-HIL
    connectorPortTypeIsDB9(8),                  -- type is DB-9
    connectorPortTypeIsAccessBusUSB(9),         -- type is Access Bus USB
    connectorPortTypeIsPC98(10)                 -- type is PC-98
}

KeyboardPortTableEntry                          ::= SEQUENCE {
    keyboardPortchassisIndex                    DellObjectRange,
    keyboardPortIndex                           DellObjectRange,
    keyboardPortStateCapabilities               DellStateCapabilities,
    keyboardPortStateSettings                   DellStateSettings,
    keyboardPortStatus                          DellStatus,
    keyboardPortSecurityState                   DellPortSecurityState,
    keyboardPortConnectorType                   DellKeyboardPortConnectorType,
    keyboardPortName                            DellString,
    keyboardPortBIOSConnectorType               DellGenericPortConnectorType
}

keyboardPortTable                               OBJECT-TYPE
    SYNTAX      SEQUENCE OF KeyboardPortTableEntry
    ACCESS      not-accessible
    STATUS      mandatory
    DESCRIPTION
"1000.0020 This object defines the Keyboard Port Table."
    ::= { portGroup 20 }
keyboardPortTableEntry                          OBJECT-TYPE
    SYNTAX      KeyboardPortTableEntry
    ACCESS      not-accessible
    STATUS      mandatory
    DESCRIPTION
"1000.0020.0001 This object defines the Keyboard Port Table Entry."
    INDEX       { keyboardPortchassisIndex,
                  keyboardPortIndex }
    ::= { keyboardPortTable 1 }

keyboardPortchassisIndex                        OBJECT-TYPE
    SYNTAX      DellObjectRange
    ACCESS      read-only
    STATUS      mandatory
    DESCRIPTION
"1000.0020.0001.0001 This attribute defines the index (one based) of the
associated chassis."
    ::= { keyboardPortTableEntry 1 }
keyboardPortIndex                               OBJECT-TYPE
    SYNTAX      DellObjectRange
    ACCESS      read-only
    STATUS      mandatory
    DESCRIPTION
"1000.0020.0001.0002 This attribute defines the index (one based) of the
keyboard port."
    ::= { keyboardPortTableEntry 2 }
keyboardPortStateCapabilities                   OBJECT-TYPE
    SYNTAX      DellStateCapabilities
    ACCESS      read-only
    STATUS      mandatory
    DESCRIPTION
"1000.0020.0001.0003 This attribute defines the state capabilities of the
keyboard port."
    ::= { keyboardPortTableEntry 3 }
keyboardPortStateSettings                       OBJECT-TYPE
    SYNTAX      DellStateSettings
    ACCESS      read-only
    STATUS      mandatory
    DESCRIPTION
"1000.0020.0001.0004 This attribute defines the state settings of the
keyboard port."
    ::= { keyboardPortTableEntry 4 }
keyboardPortStatus                              OBJECT-TYPE
    SYNTAX      DellStatus
    ACCESS      read-only
    STATUS      mandatory
    DESCRIPTION
"1000.0020.0001.0005 This attribute defines the status of the
keyboard port."
    ::= { keyboardPortTableEntry 5 }
keyboardPortSecurityState                       OBJECT-TYPE
    SYNTAX      DellPortSecurityState
    ACCESS      read-only
    STATUS      mandatory
    DESCRIPTION
"1000.0020.0001.0006 This attribute defines the security state of the
keyboard port."
    ::= { keyboardPortTableEntry 6 }
keyboardPortConnectorType                       OBJECT-TYPE
    SYNTAX      DellKeyboardPortConnectorType
    ACCESS      read-only
    STATUS      mandatory
    DESCRIPTION
"1000.0020.0001.0007 This attribute defines the connector type of the
keyboard port."
    ::= { keyboardPortTableEntry 7 }
keyboardPortName                                OBJECT-TYPE
    SYNTAX      DellString
    ACCESS      read-only
    STATUS      mandatory
    DESCRIPTION
"1000.0020.0001.0008 This attribute defines name of the keyboard port."
    ::= { keyboardPortTableEntry 8 }
keyboardPortBIOSConnectorType                   OBJECT-TYPE
    SYNTAX      DellGenericPortConnectorType
    ACCESS      read-only
    STATUS      mandatory
    DESCRIPTION
"1000.0020.0001.0009 This attribute defines the BIOS connector type of the
keyboard port."
    ::= { keyboardPortTableEntry 9 }


-------------------------------------------------------------------------------
-- Processor Port Table
--
-- OID Format: 1.3.6.1.4.1.674.10892.1.1000.30.1.<a>.<i1>.<i2>
-------------------------------------------------------------------------------

DellProcessorPortConnectorType                  ::= INTEGER {
    connectorPortTypeIsOther(1),                -- type is other than following values
    connectorPortTypeIsUnknown(2),              -- type is unknown
    connectorPortTypeIsDaughterdBoard(3),       -- type is Daughter Board
    connectorPortTypeIsZIFSocket(4),            -- type is Zero Insertion Force Socket
    connectorPortTypeIsAPiggyBackBoard(5),      -- type is Replacement/Piggy Back Board
    connectorPortTypeIsNone(6),                 -- type is None (soldered in place)
    connectorPortTypeIsLIFSocket(7),            -- type is Low Force Insertion Socket
    connectorPortTypeIsSlot1(8),                -- type is Slot 1
    connectorPortTypeIsSlot2(9),                -- type is Slot 2
    connectorPortTypeIs370PinSocket(10)         -- type is 370 Pin Socket
}

ProcessorPortTableEntry                         ::= SEQUENCE {
    processorPortchassisIndex                   DellObjectRange,
    processorPortIndex                          DellObjectRange,
    processorPortStateCapabilities              DellStateCapabilities,
    processorPortStateSettings                  DellStateSettings,
    processorPortStatus                         DellStatus,
    processorPortSecurityState                  DellPortSecurityState,
    processorPortConnectorType                  DellProcessorPortConnectorType,
    processorPortName                           DellString,
    processorPortBIOSConnectorType              DellGenericPortConnectorType
}

processorPortTable                              OBJECT-TYPE
    SYNTAX      SEQUENCE OF ProcessorPortTableEntry
    ACCESS      not-accessible
    STATUS      mandatory
    DESCRIPTION
"1000.0030 This object defines the Processor Port Table."
    ::= { portGroup 30 }
processorPortTableEntry                         OBJECT-TYPE
    SYNTAX      ProcessorPortTableEntry
    ACCESS      not-accessible
    STATUS      mandatory
    DESCRIPTION
"1000.0030.0001 This object defines the Processor Port Table Entry."
    INDEX       { processorPortchassisIndex,
                  processorPortIndex }
    ::= { processorPortTable 1 }

processorPortchassisIndex                       OBJECT-TYPE
    SYNTAX      DellObjectRange
    ACCESS      read-only
    STATUS      mandatory
    DESCRIPTION
"1000.0030.0001.0001 This attribute defines the index (one based) of the
associated chassis."
    ::= { processorPortTableEntry 1 }
processorPortIndex                              OBJECT-TYPE
    SYNTAX      DellObjectRange
    ACCESS      read-only
    STATUS      mandatory
    DESCRIPTION
"1000.0030.0001.0002 This attribute defines the index (one based) of the
processor port."
    ::= { processorPortTableEntry 2 }
processorPortStateCapabilities                  OBJECT-TYPE
    SYNTAX      DellStateCapabilities
    ACCESS      read-only
    STATUS      mandatory
    DESCRIPTION
"1000.0030.0001.0003 This attribute defines the state capabilities of the
processor port."
    ::= { processorPortTableEntry 3 }
processorPortStateSettings                      OBJECT-TYPE
    SYNTAX      DellStateSettings
    ACCESS      read-write
    STATUS      mandatory
    DESCRIPTION
"1000.0030.0001.0004 This attribute defines the state settings of the
processor port."
    ::= { processorPortTableEntry 4 }
processorPortStatus                             OBJECT-TYPE
    SYNTAX      DellStatus
    ACCESS      read-only
    STATUS      mandatory
    DESCRIPTION
"1000.0030.0001.0005 This attribute defines the status of the
processor port."
    ::= { processorPortTableEntry 5 }
processorPortSecurityState                      OBJECT-TYPE
    SYNTAX      DellPortSecurityState
    ACCESS      read-only
    STATUS      mandatory
    DESCRIPTION
"1000.0030.0001.0006 This attribute defines the security state of the
processor port."
    ::= { processorPortTableEntry 6 }
processorPortConnectorType                      OBJECT-TYPE
    SYNTAX      DellProcessorPortConnectorType
    ACCESS      read-only
    STATUS      mandatory
    DESCRIPTION
"1000.0030.0001.0007 This attribute defines the connector type of the
processor port."
    ::= { processorPortTableEntry 7 }
processorPortName                               OBJECT-TYPE
    SYNTAX      DellString
    ACCESS      read-only
    STATUS      mandatory
    DESCRIPTION
"1000.0030.0001.0008 This attribute defines name of the processor port."
    ::= { processorPortTableEntry 8 }
processorPortBIOSConnectorType                  OBJECT-TYPE
    SYNTAX      DellGenericPortConnectorType
    ACCESS      read-only
    STATUS      mandatory
    DESCRIPTION
"1000.0030.0001.0009 This attribute defines the BIOS connector type of the
processor port."
    ::= { processorPortTableEntry 9 }


-------------------------------------------------------------------------------
-- Memory Device Port Table
--
-- OID Format: 1.3.6.1.4.1.674.10892.1.1000.40.1.<a>.<i1>.<i2>
-------------------------------------------------------------------------------

DellMemoryDevicePortConnectorType               ::= INTEGER {
    connectorPortTypeIsOther(1),                -- type is other than following values
    connectorPortTypeIsUnknown(2),              -- type is unknown
    connectorPortTypeIsSIMM(3),                 -- type is SIMM
    connectorPortTypeIsSIP(4),                  -- type is SIP
    connectorPortTypeIsAChip(5),                -- type is Chip
    connectorPortTypeIsDIP(6),                  -- type is DIP
    connectorPortTypeIsZIP(7),                  -- type is ZIP
    connectorPortTypeIsAProprietaryCard(8),     -- type is Proprietary Card
    connectorPortTypeIsDIMM(9),                 -- type is DIMM
    connectorPortTypeIsTSOP(10),                -- type is TSOP
    connectorPortTypeIsARowOfChips(11),         -- type is Row of Chips
    connectorPortTypeIsRIMM(12),                -- type is RIMM
    connectorPortTypeIsSODIMM(13),              -- type is SODIMM
    connectorPortTypeIsSRIMM(14)                -- type is SRIMM
}

MemoryDevicePortTableEntry                      ::= SEQUENCE {
    memoryDevicePortchassisIndex                DellObjectRange,
    memoryDevicePortIndex                       DellObjectRange,
    memoryDevicePortStateCapabilities           DellStateCapabilities,
    memoryDevicePortStateSettings               DellStateSettings,
    memoryDevicePortStatus                      DellStatus,
    memoryDevicePortSecurityState               DellPortSecurityState,
    memoryDevicePortConnectorType               DellMemoryDevicePortConnectorType,
    memoryDevicePortName                        DellString,
    memoryDevicePortBIOSConnectorType           DellGenericPortConnectorType,
    memoryDevicePortPhysicalMemoryArrayIndexReference DellUnsigned32BitRange,
    memoryDevicePortPhysicalMemoryCardIndexReference  DellUnsigned32BitRange
}

memoryDevicePortTable                           OBJECT-TYPE
    SYNTAX      SEQUENCE OF MemoryDevicePortTableEntry
    ACCESS      not-accessible
    STATUS      mandatory
    DESCRIPTION
"1000.0040 This object defines the Memory Device Port Table."
    ::= { portGroup 40 }
memoryDevicePortTableEntry                      OBJECT-TYPE
    SYNTAX      MemoryDevicePortTableEntry
    ACCESS      not-accessible
    STATUS      mandatory
    DESCRIPTION
"1000.0040.0001 This object defines the Memory Device Port Table Entry."
    INDEX       { memoryDevicePortchassisIndex,
                  memoryDevicePortIndex }
    ::= { memoryDevicePortTable 1 }

memoryDevicePortchassisIndex                    OBJECT-TYPE
    SYNTAX      DellObjectRange
    ACCESS      read-only
    STATUS      mandatory
    DESCRIPTION
"1000.0040.0001.0001 This attribute defines the index (one based) of the
associated chassis."
    ::= { memoryDevicePortTableEntry 1 }
memoryDevicePortIndex                           OBJECT-TYPE
    SYNTAX      DellObjectRange
    ACCESS      read-only
    STATUS      mandatory
    DESCRIPTION
"1000.0040.0001.0002 This attribute defines the index (one based) of the
memory device port."
    ::= { memoryDevicePortTableEntry 2 }
memoryDevicePortStateCapabilities               OBJECT-TYPE
    SYNTAX      DellStateCapabilities
    ACCESS      read-only
    STATUS      mandatory
    DESCRIPTION
"1000.0040.0001.0003 This attribute defines the state capabilities of the
memory device port."
    ::= { memoryDevicePortTableEntry 3 }
memoryDevicePortStateSettings                   OBJECT-TYPE
    SYNTAX      DellStateSettings
    ACCESS      read-write
    STATUS      mandatory
    DESCRIPTION
"1000.0040.0001.0004 This attribute defines the state settings of the
memory device port."
    ::= { memoryDevicePortTableEntry 4 }
memoryDevicePortStatus                          OBJECT-TYPE
    SYNTAX      DellStatus
    ACCESS      read-only
    STATUS      mandatory
    DESCRIPTION
"1000.0040.0001.0005 This attribute defines the status of the
memory device port."
    ::= { memoryDevicePortTableEntry 5 }
memoryDevicePortSecurityState                   OBJECT-TYPE
    SYNTAX      DellPortSecurityState
    ACCESS      read-only
    STATUS      mandatory
    DESCRIPTION
"1000.0040.0001.0006 This attribute defines the security state of the
memory device port."
    ::= { memoryDevicePortTableEntry 6 }
memoryDevicePortConnectorType                   OBJECT-TYPE
    SYNTAX      DellMemoryDevicePortConnectorType
    ACCESS      read-only
    STATUS      mandatory
    DESCRIPTION
"1000.0040.0001.0007 This attribute defines the connector type of the
memory device port."
    ::= { memoryDevicePortTableEntry 7 }
memoryDevicePortName                            OBJECT-TYPE
    SYNTAX      DellString
    ACCESS      read-only
    STATUS      mandatory
    DESCRIPTION
"1000.0040.0001.0008 This attribute defines name of the memory device port."
    ::= { memoryDevicePortTableEntry 8 }
memoryDevicePortBIOSConnectorType               OBJECT-TYPE
    SYNTAX      DellGenericPortConnectorType
    ACCESS      read-only
    STATUS      mandatory
    DESCRIPTION
"1000.0040.0001.0009 This attribute defines the BIOS connector type of the
memory device port."
    ::= { memoryDevicePortTableEntry 9 }
memoryDevicePortPhysicalMemoryArrayIndexReference OBJECT-TYPE
    SYNTAX      DellUnsigned32BitRange
    ACCESS      read-only
    STATUS      mandatory
    DESCRIPTION
"1000.0040.0001.0010 This attribute defines the index (one based) of the
Physical Memory Array Table entry for the physical memory array with the
same chassis index that this memory device port is associated with."
    ::= { memoryDevicePortTableEntry 10 }
memoryDevicePortPhysicalMemoryCardIndexReference OBJECT-TYPE
    SYNTAX      DellUnsigned32BitRange
    ACCESS      read-only
    STATUS      mandatory
    DESCRIPTION
"1000.0040.0001.0011 This attribute defines the index (one based) of the
Physical Memory Card Table entry for the physical memory card with the
same chassis index that this memory device port is associated with (if any)."
    ::= { memoryDevicePortTableEntry 11 }


-------------------------------------------------------------------------------
-- Monitor Port Table
--
-- OID Format: 1.3.6.1.4.1.674.10892.1.1000.50.1.<a>.<i1>.<i2>
-------------------------------------------------------------------------------

DellMonitorPortConnectorType                    ::= INTEGER {
    connectorPortTypeIsOther(1),                -- type is other than following values
    connectorPortTypeIsUnknown(2),              -- type is unknown
    connectorPortTypeIsDB15PinMale(3),          -- type is Male DB-15
    connectorPortTypeIsDB15PinFemale(4)         -- type is Female DB-15
}

MonitorPortTableEntry                           ::= SEQUENCE {
    monitorPortchassisIndex                     DellObjectRange,
    monitorPortIndex                            DellObjectRange,
    monitorPortStateCapabilities                DellStateCapabilities,
    monitorPortStateSettings                    DellStateSettings,
    monitorPortStatus                           DellStatus,
    monitorPortSecurityState                    DellPortSecurityState,
    monitorPortConnectorType                    DellMonitorPortConnectorType,
    monitorPortName                             DellString,
    monitorPortBIOSConnectorType                DellGenericPortConnectorType
}

monitorPortTable                                OBJECT-TYPE
    SYNTAX      SEQUENCE OF MonitorPortTableEntry
    ACCESS      not-accessible
    STATUS      mandatory
    DESCRIPTION
"1000.0050 This object defines the Monitor Port Table."
    ::= { portGroup 50 }
monitorPortTableEntry                           OBJECT-TYPE
    SYNTAX      MonitorPortTableEntry
    ACCESS      not-accessible
    STATUS      mandatory
    DESCRIPTION
"1000.0050.0001 This object defines the Monitor Port Table Entry."
    INDEX       { monitorPortchassisIndex,
                  monitorPortIndex }
    ::= { monitorPortTable 1 }

monitorPortchassisIndex                         OBJECT-TYPE
    SYNTAX      DellObjectRange
    ACCESS      read-only
    STATUS      mandatory
    DESCRIPTION
"1000.0050.0001.0001 This attribute defines the index (one based) of the
associated chassis."
    ::= { monitorPortTableEntry 1 }
monitorPortIndex                                OBJECT-TYPE
    SYNTAX      DellObjectRange
    ACCESS      read-only
    STATUS      mandatory
    DESCRIPTION
"1000.0050.0001.0002 This attribute defines the index (one based) of the
monitor port."
    ::= { monitorPortTableEntry 2 }
monitorPortStateCapabilities                    OBJECT-TYPE
    SYNTAX      DellStateCapabilities
    ACCESS      read-only
    STATUS      mandatory
    DESCRIPTION
"1000.0050.0001.0003 This attribute defines the state capabilities of the
monitor port."
    ::= { monitorPortTableEntry 3 }
monitorPortStateSettings                        OBJECT-TYPE
    SYNTAX      DellStateSettings
    ACCESS      read-write
    STATUS      mandatory
    DESCRIPTION
"1000.0050.0001.0004 This attribute defines the state settings of the
monitor port."
    ::= { monitorPortTableEntry 4 }
monitorPortStatus                               OBJECT-TYPE
    SYNTAX      DellStatus
    ACCESS      read-only
    STATUS      mandatory
    DESCRIPTION
"1000.0050.0001.0005 This attribute defines the status of the
monitor port."
    ::= { monitorPortTableEntry 5 }
monitorPortSecurityState                        OBJECT-TYPE
    SYNTAX      DellPortSecurityState
    ACCESS      read-only
    STATUS      mandatory
    DESCRIPTION
"1000.0050.0001.0006 This attribute defines the security state of the
monitor port."
    ::= { monitorPortTableEntry 6 }
monitorPortConnectorType                        OBJECT-TYPE
    SYNTAX      DellMonitorPortConnectorType
    ACCESS      read-only
    STATUS      mandatory
    DESCRIPTION
"1000.0050.0001.0007 This attribute defines the connector type of the
monitor port."
    ::= { monitorPortTableEntry 7 }
monitorPortName                                 OBJECT-TYPE
    SYNTAX      DellString
    ACCESS      read-only
    STATUS      mandatory
    DESCRIPTION
"1000.0050.0001.0008 This attribute defines name of the monitor port."
    ::= { monitorPortTableEntry 8 }
monitorPortBIOSConnectorType                    OBJECT-TYPE
    SYNTAX      DellGenericPortConnectorType
    ACCESS      read-only
    STATUS      mandatory
    DESCRIPTION
"1000.0050.0001.0009 This attribute defines the BIOS connector type of the
monitor port."
    ::= { monitorPortTableEntry 9 }


-------------------------------------------------------------------------------
-- Small Computer Systems Interface (SCSI) Port Table
--
-- OID Format: 1.3.6.1.4.1.674.10892.1.1000.60.1.<a>.<i1>.<i2>
-------------------------------------------------------------------------------

DellSCSIPortConnectorType                       ::= INTEGER {
    connectorPortTypeIsOther(1),                -- type is other than following valaues
    connectorPortTypeIsUnknown(2),              -- type is unknown
    connectorPortTypeIsDIN25pin(3),             -- type is DIN 25-pin
    connectorPortTypeIsDIN50pin(4),             -- type is DIN 50-pin
    connectorPortTypeIsDIN68pin(5)              -- type is DIN 68-pin
}

SCSIPortTableEntry                              ::= SEQUENCE {
    sCSIPortchassisIndex                        DellObjectRange,
    sCSIPortIndex                               DellObjectRange,
    sCSIPortStateCapabilities                   DellStateCapabilities,
    sCSIPortStateSettings                       DellStateSettings,
    sCSIPortStatus                              DellStatus,
    sCSIPortSecurityState                       DellPortSecurityState,
    sCSIPortConnectorType                       DellSCSIPortConnectorType,
    sCSIPortName                                DellString,
    sCSIPortBIOSConnectorType                   DellGenericPortConnectorType
}

sCSIPortTable                                   OBJECT-TYPE
    SYNTAX      SEQUENCE OF SCSIPortTableEntry
    ACCESS      not-accessible
    STATUS      mandatory
    DESCRIPTION
"1000.0060 This object defines the Small Computer Systems Interface (SCSI)
Port Table."
    ::= { portGroup 60 }
sCSIPortTableEntry                              OBJECT-TYPE
    SYNTAX      SCSIPortTableEntry
    ACCESS      not-accessible
    STATUS      mandatory
    DESCRIPTION
"1000.0060.0001 This object defines the Small Computer Systems Interface (SCSI)
Port Table Entry."
    INDEX       { sCSIPortchassisIndex,
                  sCSIPortIndex }
    ::= { sCSIPortTable 1 }

sCSIPortchassisIndex                            OBJECT-TYPE
    SYNTAX      DellObjectRange
    ACCESS      read-only
    STATUS      mandatory
    DESCRIPTION
"1000.0060.0001.0001 This attribute defines the index (one based) of the
associated chassis."
    ::= { sCSIPortTableEntry 1 }
sCSIPortIndex                                   OBJECT-TYPE
    SYNTAX      DellObjectRange
    ACCESS      read-only
    STATUS      mandatory
    DESCRIPTION
"1000.0060.0001.0002 This attribute defines the index (one based) of the
SCSI port."
    ::= { sCSIPortTableEntry 2 }
sCSIPortStateCapabilities                       OBJECT-TYPE
    SYNTAX      DellStateCapabilities
    ACCESS      read-only
    STATUS      mandatory
    DESCRIPTION
"1000.0060.0001.0003 This attribute defines the state capabilities of the
SCSI port."
    ::= { sCSIPortTableEntry 3 }
sCSIPortStateSettings                           OBJECT-TYPE
    SYNTAX      DellStateSettings
    ACCESS      read-write
    STATUS      mandatory
    DESCRIPTION
"1000.0060.0001.0004 This attribute defines the state settings of the
SCSI port."
    ::= { sCSIPortTableEntry 4 }
sCSIPortStatus                                  OBJECT-TYPE
    SYNTAX      DellStatus
    ACCESS      read-only
    STATUS      mandatory
    DESCRIPTION
"1000.0060.0001.0005 This attribute defines the status of the
SCSI port."
    ::= { sCSIPortTableEntry 5 }
sCSIPortSecurityState                           OBJECT-TYPE
    SYNTAX      DellPortSecurityState
    ACCESS      read-only
    STATUS      mandatory
    DESCRIPTION
"1000.0060.0001.0006 This attribute defines the security state of the
SCSI port."
    ::= { sCSIPortTableEntry 6 }
sCSIPortConnectorType                           OBJECT-TYPE
    SYNTAX      DellSCSIPortConnectorType
    ACCESS      read-only
    STATUS      mandatory
    DESCRIPTION
"1000.0060.0001.0007 This attribute defines the connector type of the
SCSI port."
    ::= { sCSIPortTableEntry 7 }
sCSIPortName                                    OBJECT-TYPE
    SYNTAX      DellString
    ACCESS      read-only
    STATUS      mandatory
    DESCRIPTION
"1000.0060.0001.0008 This attribute defines name of the SCSI port."
    ::= { sCSIPortTableEntry 8 }
sCSIPortBIOSConnectorType                       OBJECT-TYPE
    SYNTAX      DellGenericPortConnectorType
    ACCESS      read-only
    STATUS      mandatory
    DESCRIPTION
"1000.0060.0001.0009 This attribute defines the BIOS connector type of the
SCSI port."
    ::= { sCSIPortTableEntry 9 }


-------------------------------------------------------------------------------
-- Parallel Port Table
--
-- OID Format: 1.3.6.1.4.1.674.10892.1.1000.70.1.<a>.<i1>.<i2>
-------------------------------------------------------------------------------

DellParallelPortConnectorType                   ::= INTEGER {
    connectorPortTypeIsOther(1),                -- type is other than following values
    connectorPortTypeIsUnknown(2),              -- type is unknown
    connectorPortTypeIsDB25PinFemale(3),        -- type is Female DB-25, IEEE1284-A Receptical
    connectorPortTypeIsDB25PinMale(4),          -- type is Male DB-25, IEEE1284-A Plug
    connectorPortTypeIsCentronics(5),           -- type is Centronics, IEEE1284-B Receptical
    connectorPortTypeIsMiniCentronics(6),       -- type is MiniCentronics, IEEE1284-C Receptical
    connectorPortTypeIsProprietary(7),          -- type is Proprietary
    connectorPortTypeIsCentronics14(8),         -- type is Centronics 14
    connectorPortTypeIsDB36PinFemale(9),        -- type is Female DB-36
    connectorPortTypeIsMiniCentronics20(10)     -- type is MiniCentronics 20
}
DellParallelPortConnectorPinout                 ::= INTEGER {
    connectorPortPinoutIsOther(1),              -- pinout is other than following values
    connectorPortPinoutIsUnknown(2),            -- pinout is unknown
    connectorPortPinoutIsXTorAT(3),             -- pinout is XT or AT pinout compatible
    connectorPortPinoutIsPS2(4),                -- pinout is PS/2 pinout compatible
    connectorPortPinoutIsIEEE1284(5),           -- pinout is IEEE 1284 pinout compatible
    connectorPortPinoutIsProprietary(6),        -- pinout is Proprietary
    connectorPortPinoutIsPC98(7),               -- pinout is PC-98 pinout compatible
    connectorPortPinoutIsPC98Hireso(8),         -- pinout is PC-98 Hireso pinout compatible
    connectorPortPinoutIsPC98Note(9),           -- pinout is PC-98 Note pinout compatible
    connectorPortPinoutIsPC98Full(10)           -- pinout is PC-98 Full pinout compatible
}
DellParallelPortCapabilitiesUnique              ::= INTEGER {
    -- If 0 (zero), there are no parallel port capabilities
    unknown(1),                                 -- capabilities are unknown
    atCapable(2),                               -- port is AT mode capable
    ps2Capable(4),                              -- port is PS/2 mode capable
    ecpCapable(8),                              -- port is ECP mode capable
    eppCapable(16),                             -- port is EPP mode capable
    atOrPS2OrECPOrEPPCapable(30),               -- port is AT, PS/2, ECP and EPP mode capable
    pc98Capable(32),                            -- port is PC98 mode capable
    pc98HiresoCapable(64),                      -- port is PC98 Hireso mode capable
    pc98HCapable(128)                           -- port is PC98H mode capable
}

ParallelPortTableEntry                          ::= SEQUENCE {
    parallelPortchassisIndex                    DellObjectRange,
    parallelPortIndex                           DellObjectRange,
    parallelPortStateCapabilities               DellStateCapabilities,
    parallelPortStateSettings                   DellStateSettings,
    parallelPortStatus                          DellStatus,
    parallelPortSecurityState                   DellPortSecurityState,
    parallelPortConnectorType                   DellParallelPortConnectorType,
    parallelPortName                            DellString,
    parallelPortConnectorPinOut                 DellParallelPortConnectorPinout,
    parallelPortCapabilitiesUnique              DellParallelPortCapabilitiesUnique,
    parallelPortBaseIOAddress                   DellUnsigned64BitRange,
    parallelPortIRQLevel                        DellUnsigned8BitRange,
    parallelPortDMASupport                      DellBoolean
}

parallelPortTable                               OBJECT-TYPE
    SYNTAX      SEQUENCE OF ParallelPortTableEntry
    ACCESS      not-accessible
    STATUS      mandatory
    DESCRIPTION
"1000.0070 This object defines the Parallel Port Table."
    ::= { portGroup 70 }
parallelPortTableEntry                          OBJECT-TYPE
    SYNTAX      ParallelPortTableEntry
    ACCESS      not-accessible
    STATUS      mandatory
    DESCRIPTION
"1000.0070.0001 This object defines the Parallel Port Table Entry."
    INDEX       { parallelPortchassisIndex,
                  parallelPortIndex }
    ::= { parallelPortTable 1 }

parallelPortchassisIndex                        OBJECT-TYPE
    SYNTAX      DellObjectRange
    ACCESS      read-only
    STATUS      mandatory
    DESCRIPTION
"1000.0070.0001.0001 This attribute defines the index (one based) of the
associated chassis."
    ::= { parallelPortTableEntry 1 }
parallelPortIndex                               OBJECT-TYPE
    SYNTAX      DellObjectRange
    ACCESS      read-only
    STATUS      mandatory
    DESCRIPTION
"1000.0070.0001.0002 This attribute defines the index (one based) of the
parallel port."
    ::= { parallelPortTableEntry 2 }
parallelPortStateCapabilities                   OBJECT-TYPE
    SYNTAX      DellStateCapabilities
    ACCESS      read-only
    STATUS      mandatory
    DESCRIPTION
"1000.0070.0001.0003 This attribute defines the state capabilities of the
parallel port."
    ::= { parallelPortTableEntry 3 }
parallelPortStateSettings                       OBJECT-TYPE
    SYNTAX      DellStateSettings
    ACCESS      read-write
    STATUS      mandatory
    DESCRIPTION
"1000.0070.0001.0004 This attribute defines the state settings of the
parallel port."
    ::= { parallelPortTableEntry 4 }
parallelPortStatus                              OBJECT-TYPE
    SYNTAX      DellStatus
    ACCESS      read-only
    STATUS      mandatory
    DESCRIPTION
"1000.0070.0001.0005 This attribute defines the status of the
parallel port."
    ::= { parallelPortTableEntry 5 }
parallelPortSecurityState                       OBJECT-TYPE
    SYNTAX      DellPortSecurityState
    ACCESS      read-only
    STATUS      mandatory
    DESCRIPTION
"1000.0070.0001.0006 This attribute defines the security state of the
parallel port."
    ::= { parallelPortTableEntry 6 }
parallelPortConnectorType                       OBJECT-TYPE
    SYNTAX      DellParallelPortConnectorType
    ACCESS      read-only
    STATUS      mandatory
    DESCRIPTION
"1000.0070.0001.0007 This attribute defines the connector type of the
parallel port."
    ::= { parallelPortTableEntry 7 }
parallelPortName                                OBJECT-TYPE
    SYNTAX      DellString
    ACCESS      read-only
    STATUS      mandatory
    DESCRIPTION
"1000.0070.0001.0008 This attribute defines the name of the
parallel port."
    ::= { parallelPortTableEntry 8 }
parallelPortConnectorPinOut                     OBJECT-TYPE
    SYNTAX      DellParallelPortConnectorPinout
    ACCESS      read-only
    STATUS      mandatory
    DESCRIPTION
"1000.0070.0001.0009 This attribute defines the pinout of the
parallel port."
    ::= { parallelPortTableEntry 9 }
parallelPortCapabilitiesUnique                  OBJECT-TYPE
    SYNTAX      DellParallelPortCapabilitiesUnique
    ACCESS      read-only
    STATUS      mandatory
    DESCRIPTION
"1000.0070.0001.0010 This attribute defines the mode capabilities of the
parallel port."
    ::= { parallelPortTableEntry 10 }
parallelPortBaseIOAddress                       OBJECT-TYPE
    SYNTAX      DellUnsigned64BitRange
    ACCESS      read-only
    STATUS      mandatory
    DESCRIPTION
"1000.0070.0001.0011 This attribute defines the base Input/Output address of
the parallel port."
    ::= { parallelPortTableEntry 11 }
parallelPortIRQLevel                            OBJECT-TYPE
    SYNTAX      DellUnsigned8BitRange
    ACCESS      read-only
    STATUS      mandatory
    DESCRIPTION
"1000.0070.0001.0012 This attribute defines the Interrupt Request Level of
the parallel port."
    ::= { parallelPortTableEntry 12 }
parallelPortDMASupport                          OBJECT-TYPE
    SYNTAX      DellBoolean
    ACCESS      read-only
    STATUS      mandatory
    DESCRIPTION
"1000.0070.0001.0013 This attribute defines if DMA is supported by the
parallel port."
    ::= { parallelPortTableEntry 13 }


-------------------------------------------------------------------------------
-- Serial Port Table
--
-- OID Format: 1.3.6.1.4.1.674.10892.1.1000.80.1.<a>.<i1>.<i2>
-------------------------------------------------------------------------------

DellSerialPortConnectorType                     ::= INTEGER {
    connectorPortTypeIsOther(1),                -- type is other than following values
    connectorPortTypeIsUnknown(2),              -- type is unknown
    connectorPortTypeIsDB9PinMale(3),           -- type is Male DB-9
    connectorPortTypeIsDB9PinFemale(4),         -- type is Female DB-9
    connectorPortTypeIsDB25PinMale(5),          -- type is Male DB-25
    connectorPortTypeIsDB25PinFemale(6),        -- type is Female DB-25
    connectorPortTypeIsRJ11(7),                 -- type is RJ-11
    connectorPortTypeIsRJ45(8),                 -- type is RJ-45
    connectorPortTypeIsProprietary(9),          -- type is Proprietary
    connectorPortTypeIsCirdin8Male(10),         -- type is Male Circular DIN-8
    connectorPortTypeIsCirdin8Female(11),       -- type is Female Circular DIN-8
    connectorPortTypeIsMiniCentronics14(12),    -- type is MiniCentronics 14
    connectorPortTypeIsMiniCentronics26(13)     -- type is MiniCentronics 26
}
DellSerialPortCapabilitiesUnique                ::= INTEGER {
    other(1),                                   -- capabilities are other than following values
    unknown(2),                                 -- capabilities are unknown
    xtorATCapable(4),                           -- port is XT or AT mode capable
    c16450Capable(8),                           -- port is 16450 capable
    c16550Capable(16),                          -- port is 16550 capable
    c16550aCapable(32),                         -- port is 16550A capable
    c8251Capable(64),                           -- port is 8251 capable
    c8251FIFOCapable(128)                       -- port is 8251 FIFO capable
}

SerialPortTableEntry                            ::= SEQUENCE {
    serialPortchassisIndex                      DellObjectRange,
    serialPortIndex                             DellObjectRange,
    serialPortStateCapabilities                 DellStateCapabilities,
    serialPortStateSettings                     DellStateSettings,
    serialPortStatus                            DellStatus,
    serialPortSecurityState                     DellPortSecurityState,
    serialPortConnectorType                     DellSerialPortConnectorType,
    serialPortName                              DellString,
    serialPortMaximumSpeed                      DellUnsigned32BitRange,
    serialPortCapabilitiesUnique                DellSerialPortCapabilitiesUnique,
    serialPortBaseIOAddress                     DellUnsigned64BitRange,
    serialPortIRQLevel                          DellUnsigned8BitRange
}

serialPortTable                                 OBJECT-TYPE
    SYNTAX      SEQUENCE OF SerialPortTableEntry
    ACCESS      not-accessible
    STATUS      mandatory
    DESCRIPTION
"1000.0080 This object defines the Serial Port Table."
    ::= { portGroup 80 }
serialPortTableEntry                            OBJECT-TYPE
    SYNTAX      SerialPortTableEntry
    ACCESS      not-accessible
    STATUS      mandatory
    DESCRIPTION
"1000.0080.0001 This object defines the Serial Port Table Entry."
    INDEX       { serialPortchassisIndex,
                  serialPortIndex }
    ::= { serialPortTable 1 }

serialPortchassisIndex                          OBJECT-TYPE
    SYNTAX      DellObjectRange
    ACCESS      read-only
    STATUS      mandatory
    DESCRIPTION
"1000.0080.0001.0001 This attribute defines the index (one based) of the
associated chassis."
    ::= { serialPortTableEntry 1 }
serialPortIndex                                 OBJECT-TYPE
    SYNTAX      DellObjectRange
    ACCESS      read-only
    STATUS      mandatory
    DESCRIPTION
"1000.0080.0001.0002 This attribute defines the index (one based) of the
serial port."
    ::= { serialPortTableEntry 2 }
serialPortStateCapabilities                     OBJECT-TYPE
    SYNTAX      DellStateCapabilities
    ACCESS      read-only
    STATUS      mandatory
    DESCRIPTION
"1000.0080.0001.0003 This attribute defines the state capabilities of the
serial port."
    ::= { serialPortTableEntry 3 }
serialPortStateSettings                         OBJECT-TYPE
    SYNTAX      DellStateSettings
    ACCESS      read-write
    STATUS      mandatory
    DESCRIPTION
"1000.0080.0001.0004 This attribute defines the state settings of the
serial port."
    ::= { serialPortTableEntry 4 }
serialPortStatus                                OBJECT-TYPE
    SYNTAX      DellStatus
    ACCESS      read-only
    STATUS      mandatory
    DESCRIPTION
"1000.0080.0001.0005 This attribute defines the status of the
serial port."
    ::= { serialPortTableEntry 5 }
serialPortSecurityState                         OBJECT-TYPE
    SYNTAX      DellPortSecurityState
    ACCESS      read-only
    STATUS      mandatory
    DESCRIPTION
"1000.0080.0001.0006 This attribute defines the security state of the
serial port."
    ::= { serialPortTableEntry 6 }
serialPortConnectorType                         OBJECT-TYPE
    SYNTAX      DellSerialPortConnectorType
    ACCESS      read-only
    STATUS      mandatory
    DESCRIPTION
"1000.0080.0001.0007 This attribute defines the connector type of the
serial port."
    ::= { serialPortTableEntry 7 }
serialPortName                                  OBJECT-TYPE
    SYNTAX      DellString
    ACCESS      read-only
    STATUS      mandatory
    DESCRIPTION
"1000.0080.0001.0008 This attribute defines the name of the
serial port."
    ::= { serialPortTableEntry 8 }
serialPortMaximumSpeed                          OBJECT-TYPE
    SYNTAX      DellUnsigned32BitRange
    ACCESS      read-only
    STATUS      mandatory
    DESCRIPTION
"1000.0080.0001.0009 This attribute defines the maximum speed the serial
port can support in bits per second.  0 (zero) indicates maximum speed
is unknown."
    ::= { serialPortTableEntry 9 }
serialPortCapabilitiesUnique                    OBJECT-TYPE
    SYNTAX      DellSerialPortCapabilitiesUnique
    ACCESS      read-only
    STATUS      mandatory
    DESCRIPTION
"1000.0080.0001.0010 This attribute defines the mode capabilities of the
serial port."
    ::= { serialPortTableEntry 10 }
serialPortBaseIOAddress                         OBJECT-TYPE
    SYNTAX      DellUnsigned64BitRange
    ACCESS      read-only
    STATUS      mandatory
    DESCRIPTION
"1000.0080.0001.0011 This attribute defines the base Input/Output address of
the serial port."
    ::= { serialPortTableEntry 11 }
serialPortIRQLevel                              OBJECT-TYPE
    SYNTAX      DellUnsigned8BitRange
    ACCESS      read-only
    STATUS      mandatory
    DESCRIPTION
"1000.0080.0001.0012 This attribute defines the Interrupt Request Level of
the serial port."
    ::= { serialPortTableEntry 12 }


-------------------------------------------------------------------------------
-- Universal Serial Bus (USB) Port Table
--
-- OID Format: 1.3.6.1.4.1.674.10892.1.1000.90.1.<a>.<i1>.<i2>
-------------------------------------------------------------------------------

DellUSBPortConnectorType                        ::= INTEGER {
    connectorPortTypeIsOther(1),                -- type is other than following values
    connectorPortTypeIsUnknown(2),              -- type is unknown
    connectorPortTypeIsUSB(3)                   -- type is Universal Serial Bus
}

USBPortTableEntry                               ::= SEQUENCE {
    uSBPortchassisIndex                         DellObjectRange,
    uSBPortIndex                                DellObjectRange,
    uSBPortStateCapabilities                    DellStateCapabilities,
    uSBPortStateSettings                        DellStateSettings,
    uSBPortStatus                               DellStatus,
    uSBPortSecurityState                        DellPortSecurityState,
    uSBPortConnectorType                        DellUSBPortConnectorType,
    uSBPortName                                 DellString,
    uSBPortBIOSConnectorType                    DellGenericPortConnectorType
}

uSBPortTable                                    OBJECT-TYPE
    SYNTAX      SEQUENCE OF USBPortTableEntry
    ACCESS      not-accessible
    STATUS      mandatory
    DESCRIPTION
"1000.0090 This object defines the Universal Serial Bus (USB) Port Table."
    ::= { portGroup 90 }
uSBPortTableEntry                               OBJECT-TYPE
    SYNTAX      USBPortTableEntry
    ACCESS      not-accessible
    STATUS      mandatory
    DESCRIPTION
"1000.0090.0001 This object defines the USB Port Table Entry."
    INDEX       { uSBPortchassisIndex,
                  uSBPortIndex }
    ::= { uSBPortTable 1 }

uSBPortchassisIndex                             OBJECT-TYPE
    SYNTAX      DellObjectRange
    ACCESS      read-only
    STATUS      mandatory
    DESCRIPTION
"1000.0090.0001.0001 This attribute defines the index (one based) of the
associated chassis."
    ::= { uSBPortTableEntry 1 }
uSBPortIndex                                    OBJECT-TYPE
    SYNTAX      DellObjectRange
    ACCESS      read-only
    STATUS      mandatory
    DESCRIPTION
"1000.0090.0001.0002 This attribute defines the index (one based) of the
USB port."
    ::= { uSBPortTableEntry 2 }
uSBPortStateCapabilities                        OBJECT-TYPE
    SYNTAX      DellStateCapabilities
    ACCESS      read-only
    STATUS      mandatory
    DESCRIPTION
"1000.0090.0001.0003 This attribute defines the state capabilities of the
USB port."
    ::= { uSBPortTableEntry 3 }
uSBPortStateSettings                            OBJECT-TYPE
    SYNTAX      DellStateSettings
    ACCESS      read-write
    STATUS      mandatory
    DESCRIPTION
"1000.0090.0001.0004 This attribute defines the state settings of the
USB port."
    ::= { uSBPortTableEntry 4 }
uSBPortStatus                                   OBJECT-TYPE
    SYNTAX      DellStatus
    ACCESS      read-only
    STATUS      mandatory
    DESCRIPTION
"1000.0090.0001.0005 This attribute defines the status of the USB port."
    ::= { uSBPortTableEntry 5 }
uSBPortSecurityState                            OBJECT-TYPE
    SYNTAX      DellPortSecurityState
    ACCESS      read-only
    STATUS      mandatory
    DESCRIPTION
"1000.0090.0001.0006 This attribute defines the security state of the
USB port."
    ::= { uSBPortTableEntry 6 }
uSBPortConnectorType                            OBJECT-TYPE
    SYNTAX      DellUSBPortConnectorType
    ACCESS      read-only
    STATUS      mandatory
    DESCRIPTION
"1000.0090.0001.0007 This attribute defines the connector type of the
USB port."
    ::= { uSBPortTableEntry 7 }
uSBPortName                                     OBJECT-TYPE
    SYNTAX      DellString
    ACCESS      read-only
    STATUS      mandatory
    DESCRIPTION
"1000.0090.0001.0008 This attribute defines name of the USB port."
    ::= { uSBPortTableEntry 8 }
uSBPortBIOSConnectorType                        OBJECT-TYPE
    SYNTAX      DellGenericPortConnectorType
    ACCESS      read-only
    STATUS      mandatory
    DESCRIPTION
"1000.0090.0001.0009 This attribute defines the BIOS connector type of the
USB port."
    ::= { uSBPortTableEntry 9 }


-------------------------------------------------------------------------------
-- Device Group
--
-- OID Format: 1.3.6.1.4.1.674.10892.1.1100
-------------------------------------------------------------------------------


-------------------------------------------------------------------------------
-- Pointing Device Table
--
-- OID Format: 1.3.6.1.4.1.674.10892.1.1100.10.1.<a>.<i1>.<i2>
-------------------------------------------------------------------------------

DellPointingDeviceType                          ::= INTEGER {
    deviceTypeIsOther(1),                       -- type is other than following values
    deviceTypeIsUnknown(2),                     -- type is Unknown
    deviceTypeIsAMouse(3),                      -- type is Mouse
    deviceTypeIsATrackBall(4),                  -- type is Track Ball
    deviceTypeIsATrackPoint(5),                 -- type is Track Point
    deviceTypeIsAGlidePoint(6),                 -- type is Glide Point
    deviceTypeIsATouchPad(7)                    -- type is Touch Pad
}

PointingDeviceTableEntry                        ::= SEQUENCE {
    pointingDevicechassisIndex                  DellObjectRange,
    pointingDeviceIndex                         DellObjectRange,
    pointingDeviceStateCapabilities             DellStateCapabilities,
    pointingDeviceStateSettings                 DellStateSettings,
    pointingDeviceStatus                        DellStatus,
    pointingPortIndexReference                  DellObjectRange,
    pointingDeviceType                          DellPointingDeviceType,
    pointingDeviceNumberofButtons               DellUnsigned8BitRange
}

pointingDeviceTable                             OBJECT-TYPE
    SYNTAX      SEQUENCE OF PointingDeviceTableEntry
    ACCESS      not-accessible
    STATUS      mandatory
    DESCRIPTION
"1100.0010 This object defines the Pointing Device Table."
    ::= { deviceGroup 10 }
pointingDeviceTableEntry                        OBJECT-TYPE
    SYNTAX      PointingDeviceTableEntry
    ACCESS      not-accessible
    STATUS      mandatory
    DESCRIPTION
"1100.0010.0001 This object defines the Pointing Device Table Entry."
    INDEX       { pointingDevicechassisIndex,
                  pointingDeviceIndex }
    ::= { pointingDeviceTable 1 }

pointingDevicechassisIndex                      OBJECT-TYPE
    SYNTAX      DellObjectRange
    ACCESS      read-only
    STATUS      mandatory
    DESCRIPTION
"1100.0010.0001.0001 This attribute defines the index (one based) of the
associated chassis."
    ::= { pointingDeviceTableEntry 1 }
pointingDeviceIndex                             OBJECT-TYPE
    SYNTAX      DellObjectRange
    ACCESS      read-only
    STATUS      mandatory
    DESCRIPTION
"1100.0010.0001.0002 This attribute defines the index (one based) of the
pointing device."
    ::= { pointingDeviceTableEntry 2 }
pointingDeviceStateCapabilities                 OBJECT-TYPE
    SYNTAX      DellStateCapabilities
    ACCESS      read-only
    STATUS      mandatory
    DESCRIPTION
"1100.0010.0001.0003 This attribute defines the state capabilities of the
pointing device."
    ::= { pointingDeviceTableEntry 3 }
pointingDeviceStateSettings                     OBJECT-TYPE
    SYNTAX      DellStateSettings
    ACCESS      read-write
    STATUS      mandatory
    DESCRIPTION
"1100.0010.0001.0004 This attribute defines the state settings of the
pointing device."
    ::= { pointingDeviceTableEntry 4 }
pointingDeviceStatus                            OBJECT-TYPE
    SYNTAX      DellStatus
    ACCESS      read-only
    STATUS      mandatory
    DESCRIPTION
"1100.0010.0001.0005 This attribute defines the status of the pointing device."
    ::= { pointingDeviceTableEntry 5 }
pointingPortIndexReference                      OBJECT-TYPE
    SYNTAX      DellObjectRange
    ACCESS      read-only
    STATUS      mandatory
    DESCRIPTION
"1100.0010.0001.0006 This attribute defines the index (one based) of the
associated pointing port in the same chassis."
    ::= { pointingDeviceTableEntry 6 }
pointingDeviceType                              OBJECT-TYPE
    SYNTAX      DellPointingDeviceType
    ACCESS      read-only
    STATUS      mandatory
    DESCRIPTION
"1100.0010.0001.0007 This attribute defines the type of the pointing device."
    ::= { pointingDeviceTableEntry 7 }
pointingDeviceNumberofButtons                   OBJECT-TYPE
    SYNTAX      DellUnsigned8BitRange
    ACCESS      read-only
    STATUS      mandatory
    DESCRIPTION
"1100.0010.0001.0008 This attribute defines the number of buttons on the
pointing device."
    ::= { pointingDeviceTableEntry 8 }


-------------------------------------------------------------------------------
-- Keyboard Device Table
--
-- OID Format: 1.3.6.1.4.1.674.10892.1.1100.20.1.<a>.<i1>.<i2>
-------------------------------------------------------------------------------

KeyboardDeviceTableEntry                        ::= SEQUENCE {
    keyboardDevicechassisIndex                  DellObjectRange,
    keyboardDeviceIndex                         DellObjectRange,
    keyboardDeviceStateCapabilities             DellStateCapabilities,
    keyboardDeviceStateSettings                 DellStateSettings,
    keyboardDeviceStatus                        DellStatus,
    keyboardPortIndexReference                  DellObjectRange,
    keyboardDeviceTypeName                      DellString,
    keyboardDeviceLayoutName                    DellString
}

keyboardDeviceTable                             OBJECT-TYPE
    SYNTAX      SEQUENCE OF KeyboardDeviceTableEntry
    ACCESS      not-accessible
    STATUS      mandatory
    DESCRIPTION
"1100.0020 This object defines the Keyboard Device Table."
    ::= { deviceGroup 20 }
keyboardDeviceTableEntry                        OBJECT-TYPE
    SYNTAX      KeyboardDeviceTableEntry
    ACCESS      not-accessible
    STATUS      mandatory
    DESCRIPTION
"1100.0020.0001 This object defines the Keyboard Device Table Entry."
    INDEX       { keyboardDevicechassisIndex,
                  keyboardDeviceIndex }
    ::= { keyboardDeviceTable 1 }

keyboardDevicechassisIndex                      OBJECT-TYPE
    SYNTAX      DellObjectRange
    ACCESS      read-only
    STATUS      mandatory
    DESCRIPTION
"1100.0020.0001.0001 This attribute defines the index (one based) of the
associated chassis."
    ::= { keyboardDeviceTableEntry 1 }
keyboardDeviceIndex                             OBJECT-TYPE
    SYNTAX      DellObjectRange
    ACCESS      read-only
    STATUS      mandatory
    DESCRIPTION
"1100.0020.0001.0002 This attribute defines the index (one based) of the
keyboard device."
    ::= { keyboardDeviceTableEntry 2 }
keyboardDeviceStateCapabilities                 OBJECT-TYPE
    SYNTAX      DellStateCapabilities
    ACCESS      read-only
    STATUS      mandatory
    DESCRIPTION
"1100.0020.0001.0003 This attribute defines the state capabilities of the
keyboard device."
    ::= { keyboardDeviceTableEntry 3 }
keyboardDeviceStateSettings                     OBJECT-TYPE
    SYNTAX      DellStateSettings
    ACCESS      read-write
    STATUS      mandatory
    DESCRIPTION
"1100.0020.0001.0004 This attribute defines the state settings of the
keyboard device."
    ::= { keyboardDeviceTableEntry 4 }
keyboardDeviceStatus                            OBJECT-TYPE
    SYNTAX      DellStatus
    ACCESS      read-only
    STATUS      mandatory
    DESCRIPTION
"1100.0020.0001.0005 This attribute defines the status of the keyboard device."
    ::= { keyboardDeviceTableEntry 5 }
keyboardPortIndexReference                      OBJECT-TYPE
    SYNTAX      DellObjectRange
    ACCESS      read-only
    STATUS      mandatory
    DESCRIPTION
"1100.0020.0001.0006 This attribute defines the index (one based) of the
associated keyboard device in the same chassis."
    ::= { keyboardDeviceTableEntry 6 }
keyboardDeviceTypeName                          OBJECT-TYPE
    SYNTAX      DellString
    ACCESS      read-only
    STATUS      mandatory
    DESCRIPTION
"1100.0020.0001.0007 This attribute defines the name of the keyboard device
type."
    ::= { keyboardDeviceTableEntry 7 }
keyboardDeviceLayoutName                        OBJECT-TYPE
    SYNTAX      DellString
    ACCESS      read-only
    STATUS      mandatory
    DESCRIPTION
"1100.0020.0001.0008 This attribute defines the name of the keyboard device
layout."
    ::= { keyboardDeviceTableEntry 8 }


-------------------------------------------------------------------------------
-- Processor Device Table
--
-- OID Format: 1.3.6.1.4.1.674.10892.1.1100.30.1.<a>.<i1>.<i2>
-------------------------------------------------------------------------------

DellProcessorDeviceType                         ::= INTEGER {
    deviceTypeIsOther(1),                       -- type is other than following values
    deviceTypeIsUnknown(2),                     -- type is unknown
    deviceTypeIsCPU(3),                         -- type is Central Processing Unit
    deviceTypeIsMathProcessor(4),               -- type is Math Processor
    deviceTypeIsDSP(5),                         -- type is Digital Signal Processor
    deviceTypeIsAVideoProcessor(6)              -- type is Video Processor
}
DellProcessorDeviceFamily                       ::= INTEGER {
    deviceFamilyIsOther(1),                     -- family is Other
    deviceFamilyIsUnknown(2),                   -- family is Unknown
    deviceFamilyIs8086(3),                      -- family is 8086
    deviceFamilyIs80286(4),                     -- family is 80286
    deviceFamilyIsIntel386(5),                  -- family is Intel386 processor
    deviceFamilyIsIntel486(6),                  -- family is Intel486 processor
    deviceFamilyIs8087(7),                      -- family is 8087
    deviceFamilyIs80287(8),                     -- family is 80287
    deviceFamilyIs80387(9),                     -- family is 80387
    deviceFamilyIs80487(10),                    -- family is 80487
    deviceFamilyIsPentium(11),                  -- family is Pentium processor Family
    deviceFamilyIsPentiumPro(12),               -- family is Pentium Pro processor
    deviceFamilyIsPentiumII(13),                -- family is Pentium II processor
    deviceFamilyIsPentiumMMX(14),               -- family is Pentium processor with MMX technology
    deviceFamilyIsCeleron(15),                  -- family is Celeron processor
    deviceFamilyIsPentiumIIXeon(16),            -- family is Pentium II Xeon processor
    deviceFamilyIsPentiumIII(17),               -- family is Pentium III processor
    deviceFamilyIsPentiumIIIXeon(18),           -- family is Pentium III Xeon processor
    deviceFamilyIsPentiumIIISpeedStep(19),      -- family is Pentium III Processor with Intel SpeedStep Technology
    deviceFamilyIsItanium(20),                  -- family is Itanium processor
    deviceFamilyIsIntelXeon(21),                -- family is Intel Xeon
    deviceFamilyIsPentium4(22),                 -- family is Pentium 4 Processor
    deviceFamilyIsIntelXeonMP(23),              -- family is Intel Xeon processor MP
    deviceFamilyIsIntelItanium2(24),            -- family is Intel Itanium 2 processor
    deviceFamilyIsK5(25),                       -- family is K5 Family
    deviceFamilyIsK6(26),                       -- family is K6 Family
    deviceFamilyIsK6-2(27),                     -- family is K6-2
    deviceFamilyIsK6-3(28),                     -- family is K6-3
    deviceFamilyIsAMDAthlon(29),                -- family is AMD Athlon Processor Family
    deviceFamilyIsAMD2900(30),                  -- family is AMD2900 Family
    deviceFamilyIsK6-2Plus(31),                 -- family is K6-2+
    deviceFamilyIsPowerPC(32),                  -- family is Power PC Family
    deviceFamilyIsPowerPC601(33),               -- family is Power PC 601
    deviceFamilyIsPowerPC603(34),               -- family is Power PC 603
    deviceFamilyIsPowerPC603Plus(35),           -- family is Power PC 603+
    deviceFamilyIsPowerPC604(36),               -- family is Power PC 604
    deviceFamilyIsPowerPC620(37),               -- family is Power PC 620
    deviceFamilyIsPowerPCx704(38),              -- family is Power PC x704
    deviceFamilyIsPowerPC750(39),               -- family is Power PC 750
    deviceFamilyIsIntelCoreDuo(40),             -- family is Intel(R) Core(TM) Duo processor
    deviceFamilyIsIntelCoreDuoMobile(41),       -- family is Intel(R) Core(TM) Duo mobile processor
    deviceFamilyIsIntelCoreSoloMobile(42),      -- family is Intel(R) Core(TM) Solo mobile processor
    deviceFamilyIsIntelAtom(43),                -- family is Intel(R) Atom(TM) processor
    deviceFamilyIsAlpha(48),                    -- family is Alpha Family
    deviceFamilyIsAlpha21064(49),               -- family is Alpha 21064
    deviceFamilyIsAlpha21066(50),               -- family is Alpha 21066
    deviceFamilyIsAlpha21164(51),               -- family is Alpha 21164
    deviceFamilyIsAlpha21164PC(52),             -- family is Alpha 21164PC
    deviceFamilyIsAlpha21164a(53),              -- family is Alpha 21164a
    deviceFamilyIsAlpha21264(54),               -- family is Alpha 21264
    deviceFamilyIsAlpha21364(55),               -- family is Alpha 21364
    deviceFamilyIsAMDTurionIIUltraDualMobileM(56), -- family is AMD Turion(TM) II Ultra Dual-Core Mobile M Processor Family
    deviceFamilyIsAMDTurionIIDualMobileM(57),   -- family is AMD Turion(TM) II Dual-Core Mobile M Processor Family
    deviceFamilyIsAMDAthlonIIDualMobileM(58),   -- family is AMD Athlon(TM) II Dual-Core Mobile M Processor Family
    deviceFamilyIsAMDOpteron6100(59),           -- family is AMD Opteron(TM) 6100 Series Processor
    deviceFamilyIsAMDOpteron4100(60),           -- family is AMD Opteron(TM) 4100 Series Processor
    deviceFamilyIsMIPS(64),                     -- family is MIPS Family
    deviceFamilyIsMIPSR4000(65),                -- family is MIPS R4000
    deviceFamilyIsMIPSR4200(66),                -- family is MIPS R4200
    deviceFamilyIsMIPSR4400(67),                -- family is MIPS R4400
    deviceFamilyIsMIPSR4600(68),                -- family is MIPS R4600
    deviceFamilyIsMIPSR10000(69),               -- family is MIPS R10000
    deviceFamilyIsSPARC(80),                    -- family is SPARC Family
    deviceFamilyIsSuperSPARC(81),               -- family is SuperSPARC
    deviceFamilyIsmicroSPARCII(82),             -- family is microSPARC II
    deviceFamilyIsmicroSPARCIIep(83),           -- family is microSPARC IIep
    deviceFamilyIsUltraSPARC(84),               -- family is UltraSPARC
    deviceFamilyIsUltraSPARCII(85),             -- family is UltraSPARC II
    deviceFamilyIsUltraSPARCIIi(86),            -- family is UltraSPARC IIi
    deviceFamilyIsUltraSPARCIII(87),            -- family is UltraSPARC III
    deviceFamilyIsUltraSPARCIIIi(88),           -- family is UltraSPARC IIIi
    deviceFamilyIs68040(96),                    -- family is 68040 Family
    deviceFamilyIs68xxx(97),                    -- family is 68xxx
    deviceFamilyIs68000(98),                    -- family is 68000
    deviceFamilyIs68010(99),                    -- family is 68010
    deviceFamilyIs68020(100),                   -- family is 68020
    deviceFamilyIs68030(101),                   -- family is 68030
    deviceFamilyIsHobbit(112),                  -- family is Hobbit Family
    deviceFamilyIsCrusoeTM5000(120),            -- family is Crusoe TM5000 Family
    deviceFamilyIsCrusoeTM3000(121),            -- family is Crusoe TM3000 Family
    deviceFamilyIsEfficeonTM8000(122),          -- family is Efficeon TM8000 Family
    deviceFamilyIsWeitek(128),                  -- family is Weitek
    deviceFamilyIsIntelCeleronM(130),           -- family is Intel(R) Celeron(R) M processor
    deviceFamilyIsAMDAthlon64(131),             -- family is AMD Athlon 64 Processor Family
    deviceFamilyIsAMDOpteron(132),              -- family is AMD Opteron Processor Family
    deviceFamilyIsAMDSempron(133),              -- family is AMD Sempron Processor Family
    deviceFamilyIsAMDTurion64Mobile(134),       -- family is AMD Turion 64 Mobile Technology
    deviceFamilyIsDualCoreAMDOpteron(135),      -- family is Dual-Core AMD Opteron(TM) Processor Family
    deviceFamilyIsAMDAthlon64X2DualCore(136),   -- family is AMD Athlon 64 X2 Dual-Core Processor Family
    deviceFamilyIsAMDTurion64X2Mobile(137),     -- family is AMD Turion(TM) 64 X2 Mobile Technology
    deviceFamilyIsQuadCoreAMDOpteron(138),      -- family is Quad-Core AMD Opteron(TM) Processor Family
    deviceFamilyIsThirdGenerationAMDOpteron(139), -- family is Third-Generation AMD Opteron(TM) Processor Family
    deviceFamilyIsAMDPhenomFXQuadCore(140),     -- family is AMD Phenom(TM) FX Quad-Core Processor Family
    deviceFamilyIsAMDPhenomX4QuadCore(141),     -- family is AMD Phenom(TM) X4 Quad-Core Processor Family
    deviceFamilyIsAMDPhenomX2DualCore(142),     -- family is AMD Phenom(TM) X2 Dual-Core Processor Family
    deviceFamilyIsAMDAthlonX2DualCore(143),     -- family is AMD Athlon(TM) X2 Dual-Core Processor Family
    deviceFamilyIsPA-RISC(144),                 -- family is PA-RISC Family
    deviceFamilyIsPA-RISC8500(145),             -- family is PA-RISC 8500
    deviceFamilyIsPA-RISC8000(146),             -- family is PA-RISC 8000
    deviceFamilyIsPA-RISC7300LC(147),           -- family is PA-RISC 7300LC
    deviceFamilyIsPA-RISC7200(148),             -- family is PA-RISC 7200
    deviceFamilyIsPA-RISC7100LC(149),           -- family is PA-RISC 7100LC
    deviceFamilyIsPA-RISC7100(150),             -- family is PA-RISC 7100
    deviceFamilyIsV30(160),                     -- family is V30 Family
    deviceFamilyIsQuadCoreIntelXeon3200(161),   -- family is Quad-Core Intel(R) Xeon(R) processor 3200 Series
    deviceFamilyIsDualCoreIntelXeon3000(162),   -- family is Dual-Core Intel(R) Xeon(R) processor 3000 Series
    deviceFamilyIsQuadCoreIntelXeon5300(163),   -- family is Quad-Core Intel(R) Xeon(R) processor 5300 Series
    deviceFamilyIsDualCoreIntelXeon5100(164),   -- family is Dual-Core Intel(R) Xeon(R) processor 5100 Series
    deviceFamilyIsDualCoreIntelXeon5000(165),   -- family is Dual-Core Intel(R) Xeon(R) processor 5000 Series
    deviceFamilyIsDualCoreIntelXeonLV(166),     -- family is Dual-Core Intel(R) Xeon(R) processor LV
    deviceFamilyIsDualCoreIntelXeonULV(167),    -- family is Dual-Core Intel(R) Xeon(R) processor ULV
    deviceFamilyIsDualCoreIntelXeon7100(168),   -- family is Dual-Core Intel(R) Xeon(R) processor 7100 Series
    deviceFamilyIsQuadCoreIntelXeon5400(169),   -- family is Quad-Core Intel(R) Xeon(R) processor 5400 Series
    deviceFamilyIsQuadCoreIntelXeon(170),       -- family is Quad-Core Intel(R) Xeon(R) processor
    deviceFamilyIsDualCoreIntelXeon5200(171),   -- family is Dual-Core Intel(R) Xeon(R) processor 5200 Series
    deviceFamilyIsDualCoreIntelXeon7200(172),   -- family is Dual-Core Intel(R) Xeon(R) processor 7200 Series
    deviceFamilyIsQuadCoreIntelXeon7300(173),   -- family is Quad-Core Intel(R) Xeon(R) processor 7300 Series
    deviceFamilyIsQuadCoreIntelXeon7400(174),   -- family is Quad-Core Intel(R) Xeon(R) processor 7400 Series
    deviceFamilyIsMultiCoreIntelXeon7400(175),  -- family is Multi-Core Intel(R) Xeon(R) processor 7400 Series
    deviceFamilyIsM1(176),                      -- family is M1 Family
    deviceFamilyIsM2(177),                      -- family is M2 Family
    deviceFamilyIsIntelPentium4HT(179),         -- family is Intel(R) Pentium(R) 4 HT processor
    deviceFamilyIsAS400(180),                   -- family is AS400 Family
    deviceFamilyIsAMDAthlonXP(182),             -- family is AMD Athlon XP Processor Family
    deviceFamilyIsAMDAthlonMP(183),             -- family is AMD Athlon MP Processor Family
    deviceFamilyIsAMDDuron(184),                -- family is AMD Duron Processor Family
    deviceFamilyIsIntelPentiumM(185),           -- family is Intel Pentium M processor
    deviceFamilyIsIntelCeleronD(186),           -- family is Intel Celeron D processor
    deviceFamilyIsIntelPentiumD(187),           -- family is Intel Pentium D processor
    deviceFamilyIsIntelPentiumExtreme(188),     -- family is Intel Pentium Processor Extreme Edition
    deviceFamilyIsIntelCoreSolo(189),           -- family is Intel(R) Core(TM) Solo processor
    deviceFamilyIsIntelCore2(190),              -- family is Intel(R) Core(TM)2 processor
    deviceFamilyIsIntelCore2Duo(191),           -- family is Intel(R) Core(TM)2 Duo processor
    deviceFamilyIsIntelCore2Solo(192),          -- family is Intel(R) Core(TM)2 Solo processor
    deviceFamilyIsIntelCore2Extreme(193),       -- family is Intel(R) Core(TM)2 Extreme processor
    deviceFamilyIsIntelCore2Quad(194),          -- family is Intel(R) Core(TM)2 Quad processor
    deviceFamilyIsIntelCore2ExtremeMobile(195), -- family is Intel(R) Core(TM)2 Extreme mobile processor
    deviceFamilyIsIntelCore2DuoMobile(196),     -- family is Intel(R) Core(TM)2 Duo mobile processor
    deviceFamilyIsIntelCore2SoloMobile(197),    -- family is Intel(R) Core(TM)2 Solo mobile processor
    deviceFamilyIsIntelCorei7(198),             -- family is Intel(R) Core(TM) i7 processor
    deviceFamilyIsDualCoreIntelCeleron(199),    -- family is Dual-Core Intel(R) Celeron(R) Processor
    deviceFamilyIsIBM390(200),                  -- family is IBM390 Family
    deviceFamilyIsG4(201),                      -- family is G4
    deviceFamilyIsG5(202),                      -- family is G5
    deviceFamilyIsESA390G6(203),                -- family is ESA/390 G6
    deviceFamilyIszArchitectur(204),            -- family is z/Architectur base
    deviceFamilyIsIntelCorei5(205),             -- family is Intel(R) Core(TM) i5 processor
    deviceFamilyIsIntelCorei3(206),             -- family is Intel(R) Core(TM) i3 processor
    deviceFamilyIsVIAC7-M(210),                 -- family is VIA C7(TM)-M Processor Family
    deviceFamilyIsVIAC7-D(211),                 -- family is VIA C7(TM)-D Processor Family
    deviceFamilyIsVIAC7(212),                   -- family is VIA C7(TM) Processor Family
    deviceFamilyIsVIAEden(213),                 -- family is VIA Eden(TM) Processor Family
    deviceFamilyIsMultiCoreIntelXeon(214),      -- family is Multi-Core Intel(R) Xeon(R) processor
    deviceFamilyIsDualCoreIntelXeon3xxx(215),   -- family is Dual-Core Intel(R) Xeon(R) processor 3xxx Series
    deviceFamilyIsQuadCoreIntelXeon3xxx(216),   -- family is Quad-Core Intel(R) Xeon(R) processor 3xxx Series
    deviceFamilyIsVIANano(217),                 -- family is VIA Nano(TM) Processor Family
    deviceFamilyIsDualCoreIntelXeon5xxx(218),   -- family is Dual-Core Intel(R) Xeon(R) processor 5xxx Series
    deviceFamilyIsQuadCoreIntelXeon5xxx(219),   -- family is Quad-Core Intel(R) Xeon(R)  processor 5xxx Series
    deviceFamilyIsDualCoreIntelXeon7xxx(221),   -- family is Dual-Core Intel(R) Xeon(R) processor 7xxx Series
    deviceFamilyIsQuadCoreIntelXeon7xxx(222),   -- family is Quad-Core Intel(R) Xeon(R) processor 7xxx Series
    deviceFamilyIsMultiCoreIntelXeon7xxx(223),  -- family is Multi-Core Intel(R) Xeon(R) processor 7xxx Series
    deviceFamilyIsMultiCoreIntelXeon3400(224),  -- family is Multi-Core Intel(R) Xeon(R) processor 3400 Series 
    deviceFamilyIsEmbeddedAMDOpertonQuadCore(230), -- family is Embedded AMD Opteron(TM) Quad-Core Processor Family
    deviceFamilyIsAMDPhenomTripleCore(231),     -- family is AMD Phenom(TM) Triple-Core Processor Family
    deviceFamilyIsAMDTurionUltraDualCoreMobile(232), -- family is AMD Turion(TM) Ultra Dual-Core Mobile Processor Family
    deviceFamilyIsAMDTurionDualCoreMobile(233), -- family is AMD Turion(TM) Dual-Core Mobile Processor Family
    deviceFamilyIsAMDAthlonDualCore(234),       -- family is AMD Athlon(TM) Dual-Core Processor Family
    deviceFamilyIsAMDSempronSI(235),            -- family is AMD Sempron(TM) SI Processor Family
    deviceFamilyIsAMDPhenomII(236),             -- family is AMD Phenom(TM) II Processor Family
    deviceFamilyIsAMDAthlonII(237),             -- family is AMD Athlon(TM) II Processor Family
    deviceFamilyIsSixCoreAMDOpteron(238),       -- family is Six-Core AMD Opteron(TM) Processor Family
    deviceFamilyIsAMDSempronM(239),             -- family is AMD Sempron(TM) M Processor Family
    deviceFamilyIsi860(250),                    -- family is i860
    deviceFamilyIsi960(251)                     -- family is i960
}
DellProcessorDeviceStatusState                  ::= INTEGER {
    other(1),                                   -- state is other than following values
    unknown(2),                                 -- state is unknown
    enabled(3),                                 -- state is enabled
    userDisabled(4),                            -- state is disabled by user via BIOS setup
    biosDisabled(5),                            -- state is disabled by BIOS (POST error)
    idle(6)                                     -- state is idle
}
DellProcessorUpgradeInformation                 ::= INTEGER {
    processorUpgradeIsOther(1),                 -- upgrade is other than following values
    processorUpgradeIsUnknown(2),               -- upgrade is unknown
    processorUpgradeIsByDaughterBoard(3),       -- upgrade is by Daughter Board
    processorUpgradeIsByZIFSocket(4),           -- upgrade is by ZIF socket
    processorUpgradeIsByReplacement(5),         -- upgrade is by Replacement/Piggy Back
    processorUpgradeIsNone(6),                  -- upgrade is None
    processorUpgradeIsByLIFSocket(7),           -- upgrade is by LIF Socket
    processorUpgradeIsBySlot1(8),               -- upgrade is by Slot 1
    processorUpgradeIsBySlot2(9),               -- upgrade is by Slot 2
    processorUpgradeIsBy370PinSocket(10),       -- upgrade is by 370 Pin Socket
    processorUpgradeIsBySlotA(11),              -- upgrade is by Slot A
    processorUpgradeIsBySlotM(12),              -- upgrade is by Slot M
    processorUpgradeIsByScoket423(13),          -- upgrade is by Socket 423
    processorUpgradeIsBySocketA(14),            -- upgrade is by Socket A (Socket 462)
    processorUpgradeIsBySocket478(15),          -- upgrade is by Socket 478
    processorUpgradeIsBySocket754(16),          -- upgrade is by Socket 754
    processorUpgradeIsBySocket940(17),          -- upgrade is by Socket 940
    processorUpgradeIsBySocket939(18),          -- upgrade is by Socket 939
    processorUpgradeIsBySocketmPGA604(19),      -- upgrade is by Socket mPGA604
    processorUpgradeIsBySocketLGA771(20),       -- upgrade is by Socket LGA771
    processorUpgradeIsBySocketLGA775(21),       -- upgrade is by Socket LGA775
    processorUpgradeIsBySocketS1(22),           -- upgrade is by Socket S1
    processorUpgradeIsBySocketAM2(23),          -- upgrade is by Socket AM2
    processorUpgradeIsBySocketF(24),            -- upgrade is by Socket F (1207)
    processorUpgradeIsBySocketLGA1366(25)       -- upgrade is by Socket LGA1366
}

ProcessorDeviceTableEntry                       ::= SEQUENCE {
    processorDevicechassisIndex                 DellObjectRange,
    processorDeviceIndex                        DellObjectRange,
    processorDeviceStateCapabilities            DellStateCapabilities,
    processorDeviceStateSettings                DellStateSettings,
    processorDeviceStatus                       DellStatus,
    processorPortIndexReference                 DellObjectRange,
    processorDeviceType                         DellProcessorDeviceType,
    processorDeviceManufacturerName             DellString,
    processorDeviceStatusState                  DellProcessorDeviceStatusState,
    processorDeviceFamily                       DellProcessorDeviceFamily,
    processorDeviceMaximumSpeed                 DellUnsigned32BitRange,
    processorDeviceCurrentSpeed                 DellUnsigned32BitRange,
    processorDeviceExternalClockSpeed           DellUnsigned32BitRange,
    processorDeviceVoltage                      DellSigned32BitRange,
    processorDeviceUpgradeInformation           DellProcessorUpgradeInformation,
    processorDeviceVersionName                  DellString,
    processorDeviceCoreCount                    DellUnsigned32BitRange,
    processorDeviceCoreEnabledCount             DellUnsigned32BitRange,
    processorDeviceThreadCount                  DellUnsigned32BitRange,
    processorDeviceCharacteristics              DellUnsigned16BitRange,
    processorDeviceExtendedCapabilities         DellUnsigned16BitRange,
    processorDeviceExtendedSettings             DellUnsigned16BitRange,
    processorDeviceBrandName                    DellString,
    processorDeviceModelName                    DellString,
    processorDeviceSteppingName                 DellString
}

processorDeviceTable                            OBJECT-TYPE
    SYNTAX      SEQUENCE OF ProcessorDeviceTableEntry
    ACCESS      not-accessible
    STATUS      mandatory
    DESCRIPTION
"1100.0030 This object defines the Processor Device Table."
    ::= { deviceGroup 30 }
processorDeviceTableEntry                       OBJECT-TYPE
    SYNTAX      ProcessorDeviceTableEntry
    ACCESS      not-accessible
    STATUS      mandatory
    DESCRIPTION
"1100.0030.0001 This object defines the Processor Device Table Entry."
    INDEX       { processorDevicechassisIndex,
                  processorDeviceIndex }
    ::= { processorDeviceTable 1 }

processorDevicechassisIndex                     OBJECT-TYPE
    SYNTAX      DellObjectRange
    ACCESS      read-only
    STATUS      mandatory
    DESCRIPTION
"1100.0030.0001.0001 This attribute defines the index (one based) of the
associated chassis."
    ::= { processorDeviceTableEntry 1 }
processorDeviceIndex                            OBJECT-TYPE
    SYNTAX      DellObjectRange
    ACCESS      read-only
    STATUS      mandatory
    DESCRIPTION
"1100.0030.0001.0002 This attribute defines the index (one based) of the
processor device."
    ::= { processorDeviceTableEntry 2 }
processorDeviceStateCapabilities                OBJECT-TYPE
    SYNTAX      DellStateCapabilities
    ACCESS      read-only
    STATUS      mandatory
    DESCRIPTION
"1100.0030.0001.0003 This attribute defines the state capabilities of the
processor device."
    ::= { processorDeviceTableEntry 3 }
processorDeviceStateSettings                    OBJECT-TYPE
    SYNTAX      DellStateSettings
    ACCESS      read-write
    STATUS      mandatory
    DESCRIPTION
"1100.0030.0001.0004 This attribute defines the state settings of the
processor device."
    ::= { processorDeviceTableEntry 4 }
processorDeviceStatus                           OBJECT-TYPE
    SYNTAX      DellStatus
    ACCESS      read-only
    STATUS      mandatory
    DESCRIPTION
"1100.0030.0001.0005 This attribute defines the status of the
processor device."
    ::= { processorDeviceTableEntry 5 }
processorPortIndexReference                     OBJECT-TYPE
    SYNTAX      DellObjectRange
    ACCESS      read-only
    STATUS      mandatory
    DESCRIPTION
"1100.0030.0001.0006 This attribute defines the index (one based) of the
associated processor port in the same chassis."
    ::= { processorDeviceTableEntry 6 }
processorDeviceType                             OBJECT-TYPE
    SYNTAX      DellProcessorDeviceType
    ACCESS      read-only
    STATUS      mandatory
    DESCRIPTION
"1100.0030.0001.0007 This attribute defines the type of the processor device."
    ::= { processorDeviceTableEntry 7 }
processorDeviceManufacturerName                 OBJECT-TYPE
    SYNTAX      DellString
    ACCESS      read-only
    STATUS      mandatory
    DESCRIPTION
"1100.0030.0001.0008 This attribute defines the name of the manufacturer
of the processor device."
    ::= { processorDeviceTableEntry 8 }
processorDeviceStatusState                      OBJECT-TYPE
    SYNTAX      DellProcessorDeviceStatusState
    ACCESS      read-only
    STATUS      mandatory
    DESCRIPTION
"1100.0030.0001.0009 This attribute defines the status state of the
processor device."
    ::= { processorDeviceTableEntry 9 }
processorDeviceFamily                           OBJECT-TYPE
    SYNTAX      DellProcessorDeviceFamily
    ACCESS      read-only
    STATUS      mandatory
    DESCRIPTION
"1100.0030.0001.0010 This attribute defines the family of the
processor device."
    ::= { processorDeviceTableEntry 10 }
processorDeviceMaximumSpeed                     OBJECT-TYPE
    SYNTAX      DellUnsigned32BitRange
    ACCESS      read-only
    STATUS      mandatory
    DESCRIPTION
"1100.0030.0001.0011 This attribute defines the maximum speed of the
processor device in MHz.  Zero indicates the maximum speed is unknown."
    ::= { processorDeviceTableEntry 11 }
processorDeviceCurrentSpeed                     OBJECT-TYPE
    SYNTAX      DellUnsigned32BitRange
    ACCESS      read-only
    STATUS      mandatory
    DESCRIPTION
"1100.0030.0001.0012 This attribute defines the current speed of the
processor device in MHz.  Zero indicates the current speed is unknown."
    ::= { processorDeviceTableEntry 12 }
processorDeviceExternalClockSpeed               OBJECT-TYPE
    SYNTAX      DellUnsigned32BitRange
    ACCESS      read-only
    STATUS      mandatory
    DESCRIPTION
"1100.0030.0001.0013 This attribute defines the speed of the
external clock for the processor device in MHz.  Zero indicates
the external clock speed is unknown."
    ::= { processorDeviceTableEntry 13 }
processorDeviceVoltage                          OBJECT-TYPE
    SYNTAX      DellSigned32BitRange
    ACCESS      read-only
    STATUS      mandatory
    DESCRIPTION
"1100.0030.0001.0014 This attribute defines the voltage powering the
processor device in millivolts.  Zero indicates the voltage is unknown."
    ::= { processorDeviceTableEntry 14 }
processorDeviceUpgradeInformation               OBJECT-TYPE
    SYNTAX      DellProcessorUpgradeInformation
    ACCESS      read-only
    STATUS      mandatory
    DESCRIPTION
"1100.0030.0001.0015 This attribute defines the processor upgrade
information for the processor device."
    ::= { processorDeviceTableEntry 15 }
processorDeviceVersionName                      OBJECT-TYPE
    SYNTAX      DellString
    ACCESS      read-only
    STATUS      mandatory
    DESCRIPTION
"1100.0030.0001.0016 This attribute defines the version of the
processor device.  On some systems, this value contains the
brand and stepping information; on other systems, this value
contains the model and stepping information."
    ::= { processorDeviceTableEntry 16 }
processorDeviceCoreCount                        OBJECT-TYPE
    SYNTAX      DellUnsigned32BitRange
    ACCESS      read-only
    STATUS      mandatory
    DESCRIPTION
"1100.0030.0001.0017 This attribute defines the number of processor cores
detected for the processor device."
    ::= { processorDeviceTableEntry 17 }
processorDeviceCoreEnabledCount                 OBJECT-TYPE
    SYNTAX      DellUnsigned32BitRange
    ACCESS      read-only
    STATUS      mandatory
    DESCRIPTION
"1100.0030.0001.0018 This attribute defines the number of processor cores
enabled for the processor device."
    ::= { processorDeviceTableEntry 18 }
processorDeviceThreadCount                      OBJECT-TYPE
    SYNTAX      DellUnsigned32BitRange
    ACCESS      read-only
    STATUS      mandatory
    DESCRIPTION
"1100.0030.0001.0019 This attribute defines the number of processor threads
detected for the processor device."
    ::= { processorDeviceTableEntry 19 }
processorDeviceCharacteristics                  OBJECT-TYPE
    SYNTAX      DellUnsigned16BitRange
    ACCESS      read-only
    STATUS      mandatory
    DESCRIPTION
"1100.0030.0001.0020 This attribute defines characteristics of the
processor device.  This attribute is a bit field where a bit has the meaning
defined below when set to 1 (one).

NOTE: Bits 2-15 need to be examined in the context of bit 1.
If bit 1 is set, the processor charactistics are unknown and bits 2-15 cannot
be used to determine if the functions associated with the bits are supported.

    Bit
    Position    Meaning if Set
    --------    --------------
    Bit 0       Reserved
    Bit 1       Unknown
    Bit 2       64-bit capable
    Bit 3-15    Reserved"
    ::= { processorDeviceTableEntry 20 }
processorDeviceExtendedCapabilities             OBJECT-TYPE
    SYNTAX      DellUnsigned16BitRange
    ACCESS      read-only
    STATUS      mandatory
    DESCRIPTION
"1100.0030.0001.0021 This attribute defines extended capabilities of the
processor device.  This attribute is a bit field where a bit has the meaning
defined below when set to 1 (one).

    Bit
    Position    Meaning if Set
    --------    --------------
    Bit 0       Virtualization Technology (VT) supported
    Bit 1       Demand-Based Switching (DBS) supported
    Bit 2       eXecute Disable (XD) supported
    Bit 3       Hyper-Threading (HT) supported"
    ::= { processorDeviceTableEntry 21 }
processorDeviceExtendedSettings                 OBJECT-TYPE
    SYNTAX      DellUnsigned16BitRange
    ACCESS      read-only
    STATUS      mandatory
    DESCRIPTION
"1100.0030.0001.0022 This attribute defines extended settings of the
processor device.  This attribute is a bit field where a bit has the meaning
defined below when set to 1 (one).

    Bit
    Position    Meaning if Set
    --------    --------------
    Bit 0       Virtualization Technology (VT) enabled
    Bit 1       Demand Based Switching (DBS) enabled
    Bit 2       eXecute Disable (XD) enabled
    Bit 3       Hyper-Threading (HT) enabled"
    ::= { processorDeviceTableEntry 22 }
processorDeviceBrandName                        OBJECT-TYPE
    SYNTAX      DellString
    ACCESS      read-only
    STATUS      mandatory
    DESCRIPTION
"1100.0030.0001.0023 This attribute defines the brand of the
processor device."
    ::= { processorDeviceTableEntry 23 }
processorDeviceModelName                        OBJECT-TYPE
    SYNTAX      DellString
    ACCESS      read-only
    STATUS      mandatory
    DESCRIPTION
"1100.0030.0001.0024 This attribute defines the model of the
processor device."
    ::= { processorDeviceTableEntry 24 }
processorDeviceSteppingName                     OBJECT-TYPE
    SYNTAX      DellString
    ACCESS      read-only
    STATUS      mandatory
    DESCRIPTION
"1100.0030.0001.0025 This attribute defines the stepping of the
processor device."
    ::= { processorDeviceTableEntry 25 }


-------------------------------------------------------------------------------
-- Processor Device Status Table
--
-- OID Format: 1.3.6.1.4.1.674.10892.1.1100.32.1.<a>.<i1>.<i2>
-------------------------------------------------------------------------------

DellProcessorDeviceStatusReading                ::= INTEGER {
    -- Note: These values are bit masks, so combination values are possible.
    internalError(1),                           -- Internal Error
    thermalTrip(2),                             -- Thermal Trip
    configurationError(32),                     -- Configuration Error
    processorPresent(128),                      -- Processor Present
    processorDisabled(256),                     -- Processor Disabled
    terminatorPresent(512),                     -- Terminator Present
    processorThrottled(1024)                    -- Processor Throttled
}

ProcessorDeviceStatusTableEntry                 ::= SEQUENCE {
    processorDeviceStatusChassisIndex           DellObjectRange,
    processorDeviceStatusIndex                  DellObjectRange,
    processorDeviceStatusStateCapabilities      DellStateCapabilities,
    processorDeviceStatusStateSettings          DellStateSettings,
    processorDeviceStatusStatus                 DellStatus,
    processorDeviceStatusReading                DellProcessorDeviceStatusReading,
    processorDeviceStatusLocationName           DellString,
    processorDeviceStatusPortIndexReference     DellObjectRange
}

processorDeviceStatusTable                      OBJECT-TYPE
    SYNTAX      SEQUENCE OF ProcessorDeviceStatusTableEntry
    ACCESS      not-accessible
    STATUS      mandatory
    DESCRIPTION
"1100.0032 This object defines the Processor Device Status Table."
    ::= { deviceGroup 32 }
processorDeviceStatusTableEntry                 OBJECT-TYPE
    SYNTAX      ProcessorDeviceStatusTableEntry
    ACCESS      not-accessible
    STATUS      mandatory
    DESCRIPTION
"1100.0032.0001 This object defines the Processor Device Status Table Entry."
    INDEX       { processorDeviceStatusChassisIndex,
                  processorDeviceStatusIndex }
    ::= { processorDeviceStatusTable 1 }

processorDeviceStatusChassisIndex               OBJECT-TYPE
    SYNTAX      DellObjectRange
    ACCESS      read-only
    STATUS      mandatory
    DESCRIPTION
"1100.0032.0001.0001 This attribute defines the index (one based) of the
associated chassis."
    ::= { processorDeviceStatusTableEntry 1 }
processorDeviceStatusIndex                      OBJECT-TYPE
    SYNTAX      DellObjectRange
    ACCESS      read-only
    STATUS      mandatory
    DESCRIPTION
"1100.0032.0001.0002 This attribute defines the index (one based) of the
processor device status probe."
    ::= { processorDeviceStatusTableEntry 2 }
processorDeviceStatusStateCapabilities          OBJECT-TYPE
    SYNTAX      DellStateCapabilities
    ACCESS      read-only
    STATUS      mandatory
    DESCRIPTION
"1100.0032.0001.0003 This attribute defines the state capabilities of the
processor device status probe."
    ::= { processorDeviceStatusTableEntry 3 }
processorDeviceStatusStateSettings              OBJECT-TYPE
    SYNTAX      DellStateSettings
    ACCESS      read-write
    STATUS      mandatory
    DESCRIPTION
"1100.0032.0001.0004 This attribute defines the state settings of the
processor device status probe."
    ::= { processorDeviceStatusTableEntry 4 }
processorDeviceStatusStatus                     OBJECT-TYPE
    SYNTAX      DellStatus
    ACCESS      read-only
    STATUS      mandatory

    DESCRIPTION
"1100.0032.0001.0005 This attribute defines the status of the
processor device status probe.  This status will be joined into
the processorDeviceStatus attribute."
    ::= { processorDeviceStatusTableEntry 5 }
processorDeviceStatusReading                    OBJECT-TYPE
    SYNTAX      DellProcessorDeviceStatusReading
    ACCESS      read-only
    STATUS      mandatory
    DESCRIPTION
"1100.0032.0001.0006 This attribute defines the reading of the
processor device status probe."
    ::= { processorDeviceStatusTableEntry 6 }
processorDeviceStatusLocationName               OBJECT-TYPE
    SYNTAX      DellString
    ACCESS      read-only
    STATUS      mandatory
    DESCRIPTION
"1100.0032.0001.0007 This attribute defines the location name of the
processor device status probe."
    ::= { processorDeviceStatusTableEntry 7 }
processorDeviceStatusPortIndexReference         OBJECT-TYPE
    SYNTAX      DellObjectRange
    ACCESS      read-only
    STATUS      mandatory
    DESCRIPTION
"1100.0032.0001.0008 This attribute defines the index (one based) of the
associated processor port in the same chassis."
    ::= { processorDeviceStatusTableEntry 8 }


-------------------------------------------------------------------------------
-- Cache Device Table
--
-- OID Format: 1.3.6.1.4.1.674.10892.1.1100.40.1.<a>.<i1>.<i2>
-------------------------------------------------------------------------------

DellCacheDeviceType                             ::= INTEGER {
    deviceTypeIsOther(1),                       -- type is other than following values
    deviceTypeIsUnknown(2),                     -- type is unknown
    deviceTypeIsInstruction(3),                 -- type is instruction
    deviceTypeIsData(4),                        -- type is data
    deviceTypeIsUnified(5)                      -- type is unified
}
DellCacheDeviceLevel                            ::= INTEGER {
    deviceLevelIsOther(1),                      -- level is other than following values
    deviceLevelIsUnknown(2),                    -- level is unknown
    deviceLevelIsPrimary(3),                    -- level is primary
    deviceLevelIsSecondary(4),                  -- level is secondary
    deviceLevelIsTertiary(5)                    -- level is tertiary
}
DellCacheDeviceWritePolicy                      ::= INTEGER {
    deviceWritePolicyIsOther(1),                -- policy is other than following values
    deviceWritePolicyIsUnknown(2),              -- policy is unknown
    deviceWritePolicyIsWriteBack(3),            -- policy is write back
    deviceWritePolicyIsWriteThrough(4),         -- policy is write through
    deviceWritePolicyIsVariesByAddress(5),      -- policy is varies by address
    deviceWritePolicyIsDeterminedByIO(6)        -- policy is determined by I/O query
}
DellCacheDeviceStatusState                      ::= INTEGER {
    other(1),                                   -- state is other than following values
    unknown(2),                                 -- state is unknown
    enabled(3),                                 -- state is enabled
    userDisabled(4),                            -- state is disabled by user
    biosDisabled(5)                             -- state is BIOS disabled
}
DellCacheDeviceECCType                          ::= INTEGER {
    deviceECCTypeIsOther(1),                    -- ECC type is other than following values
    deviceECCTypeIsUnknown(2),                  -- ECC type is unknown
    deviceECCTypeIsNone(3),                     -- ECC type is none
    deviceECCTypeIsParity(4),                   -- ECC type is parity
    deviceECCTypeIsSingleBitECC(5),             -- ECC type is single bit ECC
    deviceECCTypeIsMultiBitECC(6),              -- ECC type is multibit ECC
    deviceECCTypeIsCRC(7)                       -- ECC type is CRC
}
DellCacheDeviceAssociativity                    ::= INTEGER {
    deviceAssociativityIsOther(1),                  -- associativity is Other
    deviceAssociativityIsUnknown(2),                -- associativity is Unknown
    deviceAssociativityIsDirectMapped(3),           -- associativity is Direct Mapped
    deviceAssociativityIsTwoWaySetAssociative(4),   -- associativity is 2-way Set-Associative
    deviceAssociativityIsFourWaySetAssociative(5),  -- associativity is 4-way Set-Associative
    deviceAssociativityIsFullyAssociative(6),       -- associativity is Fully Associative
    deviceAssociativityIsEightWaySetAssociative(7), -- associativity is 8-way Set-Associative
    deviceAssociativityIsSixteenWaySetAssociative(8),   -- associativity is 16-way Set-Associative
    deviceAssociativityIs12WaySetAssociative(9),    -- associativity is 12-way Set-Associative
    deviceAssociativityIs24WaySetAssociative(10),   -- associativity is 24-way Set-Associative
    deviceAssociativityIs32WaySetAssociative(11),   -- associativity is 32-way Set-Associative
    deviceAssociativityIs48WaySetAssociative(12),   -- associativity is 48-way Set-Associative
    deviceAssociativityIs64WaySetAssociative(13)    -- associativity is 64-way Set-Associative
}
DellCacheDeviceLocation                         ::= INTEGER {
    deviceLocationIsOther(1),                   -- location is other than following values
    deviceLocationIsUnknown(2),                 -- location is unknown
    deviceLocationIsInternal(3),                -- location is internal
    deviceLocationIsExternal(4)                 -- location is external
}
DellCacheDeviceSRAMType                         ::= INTEGER {
    deviceSRAMTypeIsOther(1),                   -- SRAM type is other than following values
    deviceSRAMTypeIsUnknown(2),                 -- SRAM type is unknown
    deviceSRAMTypeIsNonBurst(3),                -- SRAM type is nonburst
    deviceSRAMTypeIsBurst(4),                   -- SRAM type is burst
    deviceSRAMTypeIsPipeBurst(5),               -- SRAM type is pipeburst
    deviceSRAMTypeIsSynchronous(6),             -- SRAM type is synchronous
    deviceSRAMTypeIsAsynchronous(7)             -- SRAM type is asynchronous
}

CacheDeviceTableEntry                           ::= SEQUENCE {
    cacheDevicechassisIndex                     DellObjectRange,
    cacheDeviceIndex                            DellObjectRange,
    cacheDeviceStateCapabilities                DellStateCapabilities,
    cacheDeviceStateSettings                    DellStateSettings,
    cacheDeviceStatus                           DellStatus,
    cacheDeviceprocessorDeviceIndexReference    DellObjectRange,
    cacheDeviceType                             DellCacheDeviceType,
    cacheDeviceLocation                         DellCacheDeviceLocation,
    cacheDeviceStatusState                      DellCacheDeviceStatusState,
    cacheDeviceExternalSocketName               DellString,
    cacheDeviceLevel                            DellCacheDeviceLevel,
    cacheDeviceMaximumSize                      DellUnsigned32BitRange,
    cacheDeviceCurrentSize                      DellUnsigned32BitRange,
    cacheDeviceSpeed                            DellUnsigned32BitRange,
    cacheDeviceWritePolicy                      DellCacheDeviceWritePolicy,
    cacheDeviceIsSocketed                       DellBoolean,
    cacheDeviceECCType                          DellCacheDeviceECCType,
    cacheDeviceAssociativity                    DellCacheDeviceAssociativity,
    cacheDeviceSupportedType                    DellCacheDeviceSRAMType,
    cacheDeviceCurrentType                      DellCacheDeviceSRAMType
}

cacheDeviceTable                                OBJECT-TYPE
    SYNTAX      SEQUENCE OF CacheDeviceTableEntry
    ACCESS      not-accessible
    STATUS      mandatory
    DESCRIPTION
"1100.0040 This object defines the Cache Device Table."
    ::= { deviceGroup 40 }
cacheDeviceTableEntry                           OBJECT-TYPE
    SYNTAX      CacheDeviceTableEntry
    ACCESS      not-accessible
    STATUS      mandatory
    DESCRIPTION
"1100.0040.0001 This object defines the Cache Device Table Entry."
    INDEX       { cacheDevicechassisIndex,
                  cacheDeviceIndex }
    ::= { cacheDeviceTable 1 }

cacheDevicechassisIndex                         OBJECT-TYPE
    SYNTAX      DellObjectRange
    ACCESS      read-only
    STATUS      mandatory
    DESCRIPTION
"1100.0040.0001.0001 This attribute defines the index (one based) of the
associated chassis."
    ::= { cacheDeviceTableEntry 1 }
cacheDeviceIndex                                OBJECT-TYPE
    SYNTAX      DellObjectRange
    ACCESS      read-only
    STATUS      mandatory
    DESCRIPTION
"1100.0040.0001.0002 This attribute defines the index (one based) of the
cache device."
    ::= { cacheDeviceTableEntry 2 }
cacheDeviceStateCapabilities                    OBJECT-TYPE
    SYNTAX      DellStateCapabilities
    ACCESS      read-only
    STATUS      mandatory
    DESCRIPTION
"1100.0040.0001.0003 This attribute defines the state capabilities of the
cache device."
    ::= { cacheDeviceTableEntry 3 }
cacheDeviceStateSettings                        OBJECT-TYPE
    SYNTAX      DellStateSettings
    ACCESS      read-write
    STATUS      mandatory
    DESCRIPTION
"1100.0040.0001.0004 This attribute defines the state settings of the
cache device."
    ::= { cacheDeviceTableEntry 4 }
cacheDeviceStatus                               OBJECT-TYPE
    SYNTAX      DellStatus
    ACCESS      read-only
    STATUS      mandatory
    DESCRIPTION
"1100.0040.0001.0005 This attribute defines the status of the cache device."
    ::= { cacheDeviceTableEntry 5 }
cacheDeviceprocessorDeviceIndexReference        OBJECT-TYPE
    SYNTAX      DellObjectRange
    ACCESS      read-only
    STATUS      mandatory
    DESCRIPTION
"1100.0040.0001.0006 This attribute defines the index (one based) of the
processor device associated with the cache device."
    ::= { cacheDeviceTableEntry 6 }
cacheDeviceType                                 OBJECT-TYPE
    SYNTAX      DellCacheDeviceType
    ACCESS      read-only
    STATUS      mandatory
    DESCRIPTION
"1100.0040.0001.0007 This attribute defines the type of cache device."
    ::= { cacheDeviceTableEntry 7 }
cacheDeviceLocation                             OBJECT-TYPE
    SYNTAX      DellCacheDeviceLocation
    ACCESS      read-only
    STATUS      mandatory
    DESCRIPTION
"1100.0040.0001.0008 This attribute defines the location of the cache device."
    ::= { cacheDeviceTableEntry 8 }
cacheDeviceStatusState                          OBJECT-TYPE
    SYNTAX      DellCacheDeviceStatusState
    ACCESS      read-only
    STATUS      mandatory
    DESCRIPTION
"1100.0040.0001.0009 This attribute defines the status state of the
cache device."
    ::= { cacheDeviceTableEntry 9 }
cacheDeviceExternalSocketName                   OBJECT-TYPE
    SYNTAX      DellString
    ACCESS      read-only
    STATUS      mandatory
    DESCRIPTION
"1100.0040.0001.0010 This attribute defines the name of the external socket
name of the cache device if the cache device is socketed."
    ::= { cacheDeviceTableEntry 10 }
cacheDeviceLevel                                OBJECT-TYPE
    SYNTAX      DellCacheDeviceLevel
    ACCESS      read-only
    STATUS      mandatory
    DESCRIPTION
"1100.0040.0001.0011 This attribute defines the level of the cache device."
    ::= { cacheDeviceTableEntry 11 }
cacheDeviceMaximumSize                          OBJECT-TYPE
    SYNTAX      DellUnsigned32BitRange
    ACCESS      read-only
    STATUS      mandatory
    DESCRIPTION
"1100.0040.0001.0012 This attribute defines the maximum size of the
cache device in KBytes.  Zero indicates the maximum size is unknown."
    ::= { cacheDeviceTableEntry 12 }
cacheDeviceCurrentSize                          OBJECT-TYPE
    SYNTAX      DellUnsigned32BitRange
    ACCESS      read-only
    STATUS      mandatory
    DESCRIPTION
"1100.0040.0001.0013 This attribute defines the current size of the
cache device in KBytes.  Zero indicates the current size is unknown."
    ::= { cacheDeviceTableEntry 13 }
cacheDeviceSpeed                                OBJECT-TYPE
    SYNTAX      DellUnsigned32BitRange
    ACCESS      read-only
    STATUS      mandatory
    DESCRIPTION
"1100.0040.0001.0014 This attribute defines the speed of the
cache device in nanoseconds.  Zero indicates the speed is unknown."
    ::= { cacheDeviceTableEntry 14 }
cacheDeviceWritePolicy                          OBJECT-TYPE
    SYNTAX      DellCacheDeviceWritePolicy
    ACCESS      read-only
    STATUS      mandatory
    DESCRIPTION
"1100.0040.0001.0015 This attribute defines the write policy of the
cache device."
    ::= { cacheDeviceTableEntry 15 }
cacheDeviceIsSocketed                           OBJECT-TYPE
    SYNTAX      DellBoolean
    ACCESS      read-only
    STATUS      mandatory
    DESCRIPTION
"1100.0040.0001.0016 This attribute defines if the cache device is
socketed or not."
    ::= { cacheDeviceTableEntry 16 }
cacheDeviceECCType                              OBJECT-TYPE
    SYNTAX      DellCacheDeviceECCType
    ACCESS      read-only
    STATUS      mandatory
    DESCRIPTION
"1100.0040.0001.0017 This attribute defines the type of error correction
in use by the cache device."
    ::= { cacheDeviceTableEntry 17 }
cacheDeviceAssociativity                        OBJECT-TYPE
    SYNTAX      DellCacheDeviceAssociativity
    ACCESS      read-only
    STATUS      mandatory
    DESCRIPTION
"1100.0040.0001.0018 This attribute defines the type of associativity
in use by the cache device."
    ::= { cacheDeviceTableEntry 18 }
cacheDeviceSupportedType                        OBJECT-TYPE
    SYNTAX      DellCacheDeviceSRAMType
    ACCESS      read-only
    STATUS      mandatory
    DESCRIPTION
"1100.0040.0001.0019 This attribute defines the supported SRAM type of the
cache device."
    ::= { cacheDeviceTableEntry 19 }
cacheDeviceCurrentType                          OBJECT-TYPE
    SYNTAX      DellCacheDeviceSRAMType
    ACCESS      read-only
    STATUS      mandatory
    DESCRIPTION
"1100.0040.0001.0020 This attribute defines the current SRAM type of the
cache device."
    ::= { cacheDeviceTableEntry 20 }


-------------------------------------------------------------------------------
-- Memory Device Table
--
-- OID Format: 1.3.6.1.4.1.674.10892.1.1100.50.1.<a>.<i1>.<i2>
-------------------------------------------------------------------------------

DellMemoryDeviceFormFactor                      ::= INTEGER {
    deviceFormFactorIsOther(1),                 -- form factor is other than following values
    deviceFormFactorIsUnknown(2),               -- form factor is unknown
    deviceFormFactorIsSIMM(3),                  -- form factor is SIMM
    deviceFormFactorIsSIP(4),                   -- form factor is SIP
    deviceFormFactorIsAChip(5),                 -- form factor is Chip
    deviceFormFactorIsDIP(6),                   -- form factor is DIP
    deviceFormFactorIsZIP(7),                   -- form factor is ZIP
    deviceFormFactorIsAProprietaryCard(8),      -- form factor is Proprietary Card
    deviceFormFactorIsDIMM(9),                  -- form factor is DIMM
    deviceFormFactorIsTSOP(10),                 -- form factor is TSOP
    deviceFormFactorIsARowOfChips(11),          -- form factor is Row of Chips
    deviceFormFactorIsRIMM(12),                 -- form factor is RIMM
    deviceFormFactorIsSODIMM(13),               -- form factor is SODIMM
    deviceFormFactorIsSRIMM(14),                -- form factor is SRIMM
    deviceFormFactorIsFBDIMM(15)                -- form factor is FB-DIMM
}
DellMemoryDeviceType                            ::= INTEGER {
    deviceTypeIsOther(1),                       -- type is other than following values
    deviceTypeIsUnknown(2),                     -- type is unknown
    deviceTypeIsDRAM(3),                        -- type is DRAM
    deviceTypeIsEDRAM(4),                       -- type is EDRAM
    deviceTypeIsVRAM(5),                        -- type is VRAM
    deviceTypeIsSRAM(6),                        -- type is SRAM
    deviceTypeIsRAM(7),                         -- type is RAM
    deviceTypeIsROM(8),                         -- type is ROM
    deviceTypeIsFLASH(9),                       -- type is FLASH
    deviceTypeIsEEPROM(10),                     -- type is EEPROM
    deviceTypeIsFEPROM(11),                     -- type is FEPROM
    deviceTypeIsEPROM(12),                      -- type is EPROM
    deviceTypeIsCDRAM(13),                      -- type is CDRAM
    deviceTypeIs3DRAM(14),                      -- type is 3DRAM
    deviceTypeIsSDRAM(15),                      -- type is SDRAM
    deviceTypeIsSGRAM(16),                      -- type is SGRAM
    deviceTypeIsRDRAM(17),                      -- type is RDRAM
    deviceTypeIsDDR(18),                        -- type is DDR
    deviceTypeIsDDR2(19),                       -- type is DDR2
    deviceTypeIsDDR2FBDIMM(20),                 -- type is DDR2 FB-DIMM
    deviceTypeIsDDR3(24),                       -- type is DDR3
    deviceTypeIsFBD2(25)                        -- type is FBD2
}
DellMemoryDeviceTypeDetails                     ::= INTEGER {
    -- Note: These values are bit masks, so combination values are possible.
    deviceTypeDetailIsOther(2),                 -- type detail is Other
    deviceTypeDetailIsUnknown(4),               -- type detail is Unknown
    deviceTypeDetailIsFastPaged(8),             -- type detail is Fast Paged
    deviceTypeDetailIsStaticColumn(16),         -- type detail is Static Column
    deviceTypeDetailIsPseudoStatic(32),         -- type detail is Pseudo-static
    deviceTypeDetailIsRAMBUS(64),               -- type detail is RAMBUS
    deviceTypeDetailIsSynchronous(128),         -- type detail is Synchronous
    deviceTypeDetailIsCMOS(256),                -- type detail is CMOS
    deviceTypeDetailIsEDO(512),                 -- type detail is EDO
    deviceTypeDetailIsWindowDRAM(1024),         -- type detail is Window DRAM
    deviceTypeDetailIsCacheDRAM(2048),          -- type detail is Cache DRAM
    deviceTypeDetailIsNonVolatile(4096),        -- type detail is Non-volatile
    deviceTypeDetailIsRegistered(8192),         -- type detail is Registered
    deviceTypeDetailIsNonRegistered(16384)      -- type detail is Non-registered
}
DellMemoryDeviceFailureModes                    ::= INTEGER {
    -- Note: These values are bit masks, so combination values are possible.
    -- If value is 0 (zero), memory device has no faults.
    eccSingleBitCorrectionWarningRate(1),       -- ECC single bit correction warning rate exceeded
    eccSingleBitCorrectionFailureRate(2),       -- ECC single bit correction failure rate exceeded
    eccMultiBitFault(4),                        -- ECC multibit fault encountered
    eccSingleBitCorrectionLoggingDisabled(8),   -- ECC single bit correction logging disabled
    deviceDisabledBySpareActivation(16)         -- device disabled because of spare activation
}

MemoryDeviceTableEntry                          ::= SEQUENCE {
    memoryDevicechassisIndex                    DellObjectRange,
    memoryDeviceIndex                           DellObjectRange,
    memoryDeviceStateCapabilities               DellStateCapabilities,
    memoryDeviceStateSettings                   DellStateSettings,
    memoryDeviceStatus                          DellStatus,
    memoryDeviceMemoryPortIndexReference        DellObjectRange,
    memoryDeviceType                            DellMemoryDeviceType,
    memoryDeviceLocationName                    DellString,
    memoryDeviceErrorCount                      DellSigned32BitRange,
    memoryDeviceBankLocationName                DellString,
    memoryDeviceTypeDetails                     DellMemoryDeviceTypeDetails,
    memoryDeviceFormFactor                      DellMemoryDeviceFormFactor,
    memoryDeviceSet                             DellUnsigned32BitRange,
    memoryDeviceSize                            DellUnsigned32BitRange,
    memoryDeviceSpeed                           DellUnsigned32BitRange,
    memoryDeviceTotalBusWidth                   DellUnsigned32BitRange,
    memoryDeviceTotalDataBusWidth               DellUnsigned32BitRange,
    memoryDeviceSingleBitErrorCount             DellSigned32BitRange,
    memoryDeviceMultiBitErrorCount              DellSigned32BitRange,
    memoryDeviceFailureModes                    DellMemoryDeviceFailureModes,
    memoryDeviceManufacturerName                DellString,
    memoryDevicePartNumberName                  DellString,
    memoryDeviceSerialNumberName                DellString,
    memoryDeviceAssetTagName                    DellString,
    memoryDeviceSpeedName                       DellString
}

memoryDeviceTable                               OBJECT-TYPE
    SYNTAX      SEQUENCE OF MemoryDeviceTableEntry
    ACCESS      not-accessible
    STATUS      mandatory
    DESCRIPTION
"1100.0050 This object defines the Memory Device Table."
    ::= { deviceGroup 50 }
memoryDeviceTableEntry                          OBJECT-TYPE
    SYNTAX      MemoryDeviceTableEntry
    ACCESS      not-accessible
    STATUS      mandatory
    DESCRIPTION
"1100.0050.0001 This object defines the Memory Device Table Entry."
    INDEX       { memoryDevicechassisIndex,
                  memoryDeviceIndex }
    ::= { memoryDeviceTable 1 }

memoryDevicechassisIndex                        OBJECT-TYPE
    SYNTAX      DellObjectRange
    ACCESS      read-only
    STATUS      mandatory
    DESCRIPTION
"1100.0050.0001.0001 This attribute defines the index (one based) of the
associated chassis."
    ::= { memoryDeviceTableEntry 1 }
memoryDeviceIndex                               OBJECT-TYPE
    SYNTAX      DellObjectRange
    ACCESS      read-only
    STATUS      mandatory
    DESCRIPTION
"1100.0050.0001.0002 This attribute defines the index (one based) of the
memory device."
    ::= { memoryDeviceTableEntry 2 }
memoryDeviceStateCapabilities                   OBJECT-TYPE
    SYNTAX      DellStateCapabilities
    ACCESS      read-only
    STATUS      mandatory
    DESCRIPTION
"1100.0050.0001.0003 This attribute defines the state capabilities of the
memory device."
    ::= { memoryDeviceTableEntry 3 }
memoryDeviceStateSettings                       OBJECT-TYPE
    SYNTAX      DellStateSettings
    ACCESS      read-write
    STATUS      mandatory
    DESCRIPTION
"1100.0050.0001.0004 This attribute defines the state settings of the
memory device."
    ::= { memoryDeviceTableEntry 4 }
memoryDeviceStatus                              OBJECT-TYPE
    SYNTAX      DellStatus
    ACCESS      read-only
    STATUS      mandatory
    DESCRIPTION
"1100.0050.0001.0005 This attribute defines the status of the memory device."
    ::= { memoryDeviceTableEntry 5 }
memoryDeviceMemoryPortIndexReference            OBJECT-TYPE
    SYNTAX      DellObjectRange
    ACCESS      read-only
    STATUS      mandatory
    DESCRIPTION
"1100.0050.0001.0006 This attribute defines the index (one based) of the
memory port that this memory device is part of."
    ::= { memoryDeviceTableEntry 6 }
memoryDeviceType                                OBJECT-TYPE
    SYNTAX      DellMemoryDeviceType
    ACCESS      read-only
    STATUS      mandatory
    DESCRIPTION
"1100.0050.0001.0007 This attribute defines the type of the memory device."
    ::= { memoryDeviceTableEntry 7 }
memoryDeviceLocationName                        OBJECT-TYPE
    SYNTAX      DellString
    ACCESS      read-only
    STATUS      mandatory
    DESCRIPTION
"1100.0050.0001.0008 This attribute defines the location of the memory device."
    ::= { memoryDeviceTableEntry 8 }
memoryDeviceErrorCount                          OBJECT-TYPE
    SYNTAX      DellSigned32BitRange
    ACCESS      read-write
    STATUS      deprecated
    DESCRIPTION
"1100.0050.0001.0009 This attribute defines the total number of ECC corrections
for the memory device.  Writing a 0 (zero) to this variable will reset
the error counts for the device.

**NOTE: This attribute is deprecated and replaced by memoryDeviceFailureModes.
The value will always be zero.  Writing a 0 (zero) has no effect."
    ::= { memoryDeviceTableEntry 9 }
memoryDeviceBankLocationName                    OBJECT-TYPE
    SYNTAX      DellString
    ACCESS      read-write
    STATUS      mandatory
    DESCRIPTION
"1100.0050.0001.0010 This attribute defines the location of the bank for the
memory device."
    ::= { memoryDeviceTableEntry 10 }
memoryDeviceTypeDetails                         OBJECT-TYPE
    SYNTAX      DellMemoryDeviceTypeDetails
    ACCESS      read-only
    STATUS      mandatory
    DESCRIPTION
"1100.0050.0001.0011 This attribute defines the detailed type of the
memory device."
    ::= { memoryDeviceTableEntry 11 }
memoryDeviceFormFactor                          OBJECT-TYPE
    SYNTAX      DellMemoryDeviceFormFactor
    ACCESS      read-only
    STATUS      mandatory
    DESCRIPTION
"1100.0050.0001.0012 This attribute defines the form factor of the
memory device."
    ::= { memoryDeviceTableEntry 12 }
memoryDeviceSet                                 OBJECT-TYPE
    SYNTAX      DellUnsigned32BitRange
    ACCESS      read-only
    STATUS      mandatory
    DESCRIPTION
"1100.0050.0001.0013 This attribute defines if the memory device is a part
of a set.  Zero indicates it is not part of a set; 2,147,483,647 indicates
it is unknown if it is a part of a set."
    ::= { memoryDeviceTableEntry 13 }
memoryDeviceSize                                OBJECT-TYPE
    SYNTAX      DellUnsigned32BitRange
    ACCESS      read-only
    STATUS      mandatory
    DESCRIPTION
"1100.0050.0001.0014 This attribute defines the size in KBytes of the
memory device.  Zero indicates no memory installed; 2,147,483,647 indicates
an unknown memory size."
    ::= { memoryDeviceTableEntry 14 }
memoryDeviceSpeed                               OBJECT-TYPE
    SYNTAX      DellUnsigned32BitRange
    ACCESS      read-only
    STATUS      mandatory
    DESCRIPTION
"1100.0050.0001.0015 This attribute defines the speed in nanoseconds
of the memory device.  Zero indicates an unknown speed."
    ::= { memoryDeviceTableEntry 15 }
memoryDeviceTotalBusWidth                       OBJECT-TYPE
    SYNTAX      DellUnsigned32BitRange
    ACCESS      read-only
    STATUS      mandatory
    DESCRIPTION
"1100.0050.0001.0016 This attribute defines the total number bits,
including ECC, used by the memory device.  2,147,483,647 indicates
an unknown number of bits."
    ::= { memoryDeviceTableEntry 16 }
memoryDeviceTotalDataBusWidth                   OBJECT-TYPE
    SYNTAX      DellUnsigned32BitRange
    ACCESS      read-only
    STATUS      mandatory
    DESCRIPTION
"1100.0050.0001.0017 This attribute defines the total number of data bits
used by the memory device.  2,147,483,647 indicates an unknown number of bits."
    ::= { memoryDeviceTableEntry 17 }
memoryDeviceSingleBitErrorCount                 OBJECT-TYPE
    SYNTAX      DellSigned32BitRange
    ACCESS      read-only
    STATUS      deprecated
    DESCRIPTION
"1100.0050.0001.0018 This attribute defines the total number of single bit
ECC corrections for the memory device.

**NOTE: This attribute is deprecated and replaced by memoryDeviceFailureModes.
The value will always be zero."
    ::= { memoryDeviceTableEntry 18 }
memoryDeviceMultiBitErrorCount                  OBJECT-TYPE
    SYNTAX      DellSigned32BitRange
    ACCESS      read-only
    STATUS      deprecated
    DESCRIPTION
"1100.0050.0001.0019 This attribute defines the total number of multibit
ECC errors for the memory device.

**NOTE: This attribute is deprecated and replaced by memoryDeviceFailureModes.
The value will always be zero."
    ::= { memoryDeviceTableEntry 19 }
memoryDeviceFailureModes                        OBJECT-TYPE
    SYNTAX      DellMemoryDeviceFailureModes
    ACCESS      read-only
    STATUS      mandatory
    DESCRIPTION
"1100.0050.0001.0020 This attribute defines the failure modes of the
memory device when the memoryDeviceStatus attribute is not ok(3).  It is
a bit field that can be used to report more than one type of failure mode
by using a combination of the defined bit masks.

**NOTE: This attribute replaces the memory device error count attributes.
When the memoryDeviceStatus attribute is not ok(3), this attribute should be
used to determine the reason for that instead of the error count attributes."
    ::= { memoryDeviceTableEntry 20 }
memoryDeviceManufacturerName                    OBJECT-TYPE
    SYNTAX      DellString
    ACCESS      read-only
    STATUS      mandatory
    DESCRIPTION
"1100.0050.0001.0021 This attribute defines the manufacturer of the
memory device."
    ::= { memoryDeviceTableEntry 21 }
memoryDevicePartNumberName                      OBJECT-TYPE
    SYNTAX      DellString
    ACCESS      read-only
    STATUS      mandatory
    DESCRIPTION
"1100.0050.0001.0022 This attribute defines the manufacturer's part number
for the memory device."
    ::= { memoryDeviceTableEntry 22 }
memoryDeviceSerialNumberName                    OBJECT-TYPE
    SYNTAX      DellString
    ACCESS      read-only
    STATUS      mandatory
    DESCRIPTION
"1100.0050.0001.0023 This attribute defines the serial number of the
memory device."
    ::= { memoryDeviceTableEntry 23 }
memoryDeviceAssetTagName                        OBJECT-TYPE
    SYNTAX      DellString
    ACCESS      read-only
    STATUS      mandatory
    DESCRIPTION
"1100.0050.0001.0024 This attribute defines the asset tag of the
memory device."
    ::= { memoryDeviceTableEntry 24 }
memoryDeviceSpeedName                           OBJECT-TYPE
    SYNTAX      DellString
    ACCESS      read-only
    STATUS      mandatory
    DESCRIPTION
"1100.0050.0001.0025 This attribute defines the speed of the memory device
in string format with units specified in string."
    ::= { memoryDeviceTableEntry 25 }


-------------------------------------------------------------------------------
-- Memory Device Mapped Address Table
--
-- OID Format: 1.3.6.1.4.1.674.10892.1.1100.60.1.<a>.<i1>.<i2>
-------------------------------------------------------------------------------

MemoryDeviceMappedAddressTableEntry             ::= SEQUENCE {
    memoryDeviceMappedAddresschassisIndex       DellObjectRange,
    memoryDeviceMappedAddressIndex              DellObjectRange,
    memoryDeviceMappedAddressStateCapabilities  DellStateCapabilities,
    memoryDeviceMappedAddressStateSettings      DellStateSettings,
    memoryDeviceMappedAddressStatus             DellStatus,
    memoryDeviceIndexReference                  DellObjectRange,
    memoryDeviceMappedAddressRowPosition        DellUnsigned32BitRange,
    memoryDeviceMappedAddressInterleavePosition DellUnsigned32BitRange,
    memoryDeviceMappedAddressInterleaveDepth    DellUnsigned32BitRange,
    memoryDeviceMappedAddressStartingAddress    DellUnsigned64BitRange,
    memoryDeviceMappedAddressEndingAddress      DellUnsigned64BitRange
}

memoryDeviceMappedAddressTable                  OBJECT-TYPE
    SYNTAX      SEQUENCE OF MemoryDeviceMappedAddressTableEntry
    ACCESS      not-accessible
    STATUS      mandatory
    DESCRIPTION
"1100.0060 This object defines the Memory Device Mapped Address Table."
    ::= { deviceGroup 60 }
memoryDeviceMappedAddressTableEntry             OBJECT-TYPE
    SYNTAX      MemoryDeviceMappedAddressTableEntry
    ACCESS      not-accessible
    STATUS      mandatory
    DESCRIPTION
"1100.0060.0001 This object defines the Memory Device Mapped Address
Table Entry."
    INDEX       { memoryDeviceMappedAddresschassisIndex,
                  memoryDeviceMappedAddressIndex }
    ::= { memoryDeviceMappedAddressTable 1 }

memoryDeviceMappedAddresschassisIndex           OBJECT-TYPE
    SYNTAX      DellObjectRange
    ACCESS      read-only
    STATUS      mandatory
    DESCRIPTION
"1100.0060.0001.0001 This attribute defines the index (one based) of the
associated chassis."
    ::= { memoryDeviceMappedAddressTableEntry 1 }
memoryDeviceMappedAddressIndex                  OBJECT-TYPE
    SYNTAX      DellObjectRange
    ACCESS      read-only
    STATUS      mandatory
    DESCRIPTION
"1100.0060.0001.0002 This attribute defines the index (one based) of the
memory device mapped address."
    ::= { memoryDeviceMappedAddressTableEntry 2 }
memoryDeviceMappedAddressStateCapabilities     OBJECT-TYPE
    SYNTAX      DellStateCapabilities
    ACCESS      read-only
    STATUS      mandatory
    DESCRIPTION
"1100.0060.0001.0003 This attribute defines the state capabilities of the
memory device mapped address."
    ::= { memoryDeviceMappedAddressTableEntry 3 }
memoryDeviceMappedAddressStateSettings          OBJECT-TYPE
    SYNTAX      DellStateSettings
    ACCESS      read-write
    STATUS      mandatory
    DESCRIPTION
"1100.0060.0001.0004 This attribute defines the state settings of the
memory device mapped address."
    ::= { memoryDeviceMappedAddressTableEntry 4 }
memoryDeviceMappedAddressStatus                 OBJECT-TYPE
    SYNTAX      DellStatus
    ACCESS      read-only
    STATUS      mandatory
    DESCRIPTION
"1100.0060.0001.0005 This attribute defines the status of the
memory device mapped address."
    ::= { memoryDeviceMappedAddressTableEntry 5 }
memoryDeviceIndexReference                     OBJECT-TYPE
    SYNTAX      DellObjectRange
    ACCESS      read-only
    STATUS      mandatory
    DESCRIPTION
"1100.0060.0001.0006 This attribute defines the index (one based) of the
memory device associated with the memory device mapped address."
    ::= { memoryDeviceMappedAddressTableEntry 6 }
memoryDeviceMappedAddressRowPosition            OBJECT-TYPE
    SYNTAX      DellUnsigned32BitRange
    ACCESS      read-only
    STATUS      mandatory
    DESCRIPTION
"1100.0060.0001.0007 This attribute defines the position of the referenced
memory in a row of the memory device mapped address.
2,147,483,647 indicates an unknown position."
    ::= { memoryDeviceMappedAddressTableEntry 7 }
memoryDeviceMappedAddressInterleavePosition     OBJECT-TYPE
    SYNTAX      DellUnsigned32BitRange
    ACCESS      read-only
    STATUS      mandatory
    DESCRIPTION
"1100.0060.0001.0008 This attribute defines the position of the referenced
memory in an interleave of the memory device mapped address.
2,147,483,647 indicates an unknown position."
    ::= { memoryDeviceMappedAddressTableEntry 8 }
memoryDeviceMappedAddressInterleaveDepth        OBJECT-TYPE
    SYNTAX      DellUnsigned32BitRange
    ACCESS      read-only
    STATUS      mandatory
    DESCRIPTION
"1100.0060.0001.0009 This attribute defines the maximum number of
consecutive rows from the referenced memory device that are accessed
in a single interleaved transfer in the memory device mapped address.
2,147,483,647 indicates an unknown number of rows."
    ::= { memoryDeviceMappedAddressTableEntry 9 }
memoryDeviceMappedAddressStartingAddress        OBJECT-TYPE
    SYNTAX      DellUnsigned64BitRange
    ACCESS      read-only
    STATUS      mandatory
    DESCRIPTION
"1100.0060.0001.0010 This attribute defines the physical starting address
in KBytes of the memory device mapped address."
    ::= { memoryDeviceMappedAddressTableEntry 10 }
memoryDeviceMappedAddressEndingAddress          OBJECT-TYPE
    SYNTAX      DellUnsigned64BitRange
    ACCESS      read-only
    STATUS      mandatory
    DESCRIPTION
"1100.0060.0001.0011 This attribute defines the physical ending address
in KBytes of the memory device mapped address."
    ::= { memoryDeviceMappedAddressTableEntry 11 }


-------------------------------------------------------------------------------
-- Generic Device Table
--
-- OID Format: 1.3.6.1.4.1.674.10892.1.1100.70.1.<a>.<i1>.<i2>
-------------------------------------------------------------------------------

DellGenericDeviceType                           ::= INTEGER {
    deviceTypeIsOther(1),                       -- type is other than following values
    deviceTypeIsUnknown(2),                     -- type is unknown
    deviceTypeIsAVideoDevice(3),                -- type is Video Device
    deviceTypeIsASCSIController(4),             -- type is SCSI Controller
    deviceTypeIsAnEthernetDevice(5),            -- type is Ethernet
    deviceTypeIsTokenRingDevice(6),             -- type is Token Ring
    deviceTypeIsASoundDevice(7)                 -- type is Sound Device
}

GenericDeviceTableEntry                         ::= SEQUENCE {
    genericDevicechassisIndex                   DellObjectRange,
    genericDeviceIndex                          DellObjectRange,
    genericDeviceStateCapabilities              DellStateCapabilities,
    genericDeviceStateSettings                  DellStateSettings,
    genericDeviceStatus                         DellStatus,
    genericDeviceSystemSlotIndexReference       DellObjectRange,
    genericDeviceType                           DellGenericDeviceType,
    genericDeviceName                           DellString
}

genericDeviceTable                              OBJECT-TYPE
    SYNTAX      SEQUENCE OF GenericDeviceTableEntry
    ACCESS      not-accessible
    STATUS      mandatory
    DESCRIPTION
"1100.0070 This object defines the Generic Device Table."
    ::= { deviceGroup 70 }
genericDeviceTableEntry                         OBJECT-TYPE
    SYNTAX      GenericDeviceTableEntry
    ACCESS      not-accessible
    STATUS      mandatory
    DESCRIPTION
"1100.0070.0001 This object defines the Generic Device Table Entry."
    INDEX       { genericDevicechassisIndex,
                  genericDeviceIndex }
    ::= { genericDeviceTable 1 }

genericDevicechassisIndex                       OBJECT-TYPE
    SYNTAX      DellObjectRange
    ACCESS      read-only
    STATUS      mandatory
    DESCRIPTION
"1100.0070.0001.0001 This attribute defines the index (one based) of the
associated chassis."
    ::= { genericDeviceTableEntry 1 }
genericDeviceIndex                              OBJECT-TYPE
    SYNTAX      DellObjectRange
    ACCESS      read-only
    STATUS      mandatory
    DESCRIPTION
"1100.0070.0001.0002 This attribute defines the index (one based) of the
generic device."
    ::= { genericDeviceTableEntry 2 }
genericDeviceStateCapabilities                  OBJECT-TYPE
    SYNTAX      DellStateCapabilities
    ACCESS      read-only
    STATUS      mandatory
    DESCRIPTION
"1100.0070.0001.0003 This attribute defines the state capabilities of the
generic device."
    ::= { genericDeviceTableEntry 3 }
genericDeviceStateSettings                      OBJECT-TYPE
    SYNTAX      DellStateSettings
    ACCESS      read-write
    STATUS      mandatory
    DESCRIPTION
"1100.0070.0001.0004 This attribute defines the state settings of the
generic device."
    ::= { genericDeviceTableEntry 4 }
genericDeviceStatus                             OBJECT-TYPE
    SYNTAX      DellStatus
    ACCESS      read-only
    STATUS      mandatory
    DESCRIPTION
"1100.0070.0001.0005 This attribute defines the status of the
generic device."
    ::= { genericDeviceTableEntry 5 }
genericDeviceSystemSlotIndexReference           OBJECT-TYPE
    SYNTAX      DellObjectRange
    ACCESS      read-only
    STATUS      mandatory
    DESCRIPTION
"1100.0070.0001.0006 This attribute defines the index (one based) of the
system slot that the generic device is in."
    ::= { genericDeviceTableEntry 6 }
genericDeviceType                               OBJECT-TYPE
    SYNTAX      DellGenericDeviceType
    ACCESS      read-only
    STATUS      mandatory
    DESCRIPTION
"1100.0070.0001.0007 This attribute defines the type of the generic device."
    ::= { genericDeviceTableEntry 7 }
genericDeviceName                               OBJECT-TYPE
    SYNTAX      DellString
    ACCESS      read-only
    STATUS      mandatory
    DESCRIPTION
"1100.0070.0001.0008 This attribute defines the name of the generic device."
    ::= { genericDeviceTableEntry 8 }


-------------------------------------------------------------------------------
-- PCI Device Table
--
-- OID Format: 1.3.6.1.4.1.674.10892.1.1100.80.1.<a>.<i1>.<i2>
-------------------------------------------------------------------------------

PCIDeviceTableEntry                             ::= SEQUENCE {
    pCIDevicechassisIndex                       DellObjectRange,
    pCIDeviceIndex                              DellObjectRange,
    pCIDeviceStateCapabilities                  DellStateCapabilities,
    pCIDeviceStateSettings                      DellStateSettings,
    pCIDeviceStatus                             DellStatus,
    pCIDeviceSystemSlotIndexReference           DellObjectRange,
    pCIDeviceDataBusWidth                       DellUnsigned32BitRange,
    pCIDeviceManufacturerName                   DellString,
    pCIDeviceDescriptionName                    DellString,
    pCIDeviceSpeed                              DellUnsigned32BitRange,
    pCIDeviceAdapterFault                       DellBoolean
}

pCIDeviceTable                                  OBJECT-TYPE
    SYNTAX      SEQUENCE OF PCIDeviceTableEntry
    ACCESS      not-accessible
    STATUS      mandatory
    DESCRIPTION
"1100.0080 This object defines the PCI Device Table."
    ::= { deviceGroup 80 }
pCIDeviceTableEntry                             OBJECT-TYPE
    SYNTAX      PCIDeviceTableEntry
    ACCESS      not-accessible
    STATUS      mandatory
    DESCRIPTION
"1100.0080.0001 This object defines the PCI Device Table Entry."
    INDEX       { pCIDevicechassisIndex,
                  pCIDeviceIndex }
    ::= { pCIDeviceTable 1 }

pCIDevicechassisIndex                           OBJECT-TYPE
    SYNTAX      DellObjectRange
    ACCESS      read-only
    STATUS      mandatory
    DESCRIPTION
"1100.0080.0001.0001 This attribute defines the index (one based) of the
associated chassis."
    ::= { pCIDeviceTableEntry 1 }
pCIDeviceIndex                                  OBJECT-TYPE
    SYNTAX      DellObjectRange
    ACCESS      read-only
    STATUS      mandatory
    DESCRIPTION
"1100.0080.0001.0002 This attribute defines the index (one based) of the
PCI device."
    ::= { pCIDeviceTableEntry 2 }
pCIDeviceStateCapabilities                      OBJECT-TYPE
    SYNTAX      DellStateCapabilities
    ACCESS      read-only
    STATUS      mandatory
    DESCRIPTION
"1100.0080.0001.0003 This attribute defines the state capabilities of the
PCI device."
    ::= { pCIDeviceTableEntry 3 }
pCIDeviceStateSettings                          OBJECT-TYPE
    SYNTAX      DellStateSettings
    ACCESS      read-write
    STATUS      mandatory
    DESCRIPTION
"1100.0080.0001.0004 This attribute defines the state settings of the
PCI device."
    ::= { pCIDeviceTableEntry 4 }
pCIDeviceStatus                                 OBJECT-TYPE
    SYNTAX      DellStatus
    ACCESS      read-only
    STATUS      mandatory
    DESCRIPTION
"1100.0080.0001.0005 This attribute defines the status of the PCI device."
    ::= { pCIDeviceTableEntry 5 }
pCIDeviceSystemSlotIndexReference               OBJECT-TYPE
    SYNTAX      DellObjectRange
    ACCESS      read-only
    STATUS      mandatory
    DESCRIPTION
"1100.0080.0001.0006 This attribute defines the index (one based) of the
system slot that the PCI Device is in."
    ::= { pCIDeviceTableEntry 6 }
pCIDeviceDataBusWidth                           OBJECT-TYPE
    SYNTAX      DellUnsigned32BitRange
    ACCESS      read-only
    STATUS      mandatory
    DESCRIPTION
"1100.0080.0001.0007 This attribute defines the width of the data bus
of the PCI device."
    ::= { pCIDeviceTableEntry 7 }
pCIDeviceManufacturerName                       OBJECT-TYPE
    SYNTAX      DellString
    ACCESS      read-only
    STATUS      mandatory
    DESCRIPTION
"1100.0080.0001.0008 This attribute defines the name of the manufacturer
of the PCI device."
    ::= { pCIDeviceTableEntry 8 }
pCIDeviceDescriptionName                        OBJECT-TYPE
    SYNTAX      DellString
    ACCESS      read-only
    STATUS      mandatory
    DESCRIPTION
"1100.0080.0001.0009 This attribute defines the description of the PCI device."
    ::= { pCIDeviceTableEntry 9 }
pCIDeviceSpeed                                  OBJECT-TYPE
    SYNTAX      DellUnsigned32BitRange
    ACCESS      read-only
    STATUS      mandatory
    DESCRIPTION
"1100.0080.0001.0010 This attribute defines the bus speed in MHz of the
PCI device.  Zero indicates the speed is unknown."
    ::= { pCIDeviceTableEntry 10 }
pCIDeviceAdapterFault                           OBJECT-TYPE
    SYNTAX      DellBoolean
    ACCESS      read-only
    STATUS      mandatory
    DESCRIPTION
"1100.0080.0001.0011 This attribute defines if the PCI device has detected
a fault or not."
    ::= { pCIDeviceTableEntry 11 }


-------------------------------------------------------------------------------
-- PCI Device Configuration Space Table
--
-- OID Format: 1.3.6.1.4.1.674.10892.1.1100.82.1.<a>.<i1>.<i2>
-------------------------------------------------------------------------------

PCIDeviceConfigurationSpaceTableEntry           ::= SEQUENCE {
    pCIDeviceConfigurationSpacechassisIndex     DellObjectRange,
    pCIDeviceConfigurationSpaceIndex            DellObjectRange,
    pCIDeviceConfigurationSpaceStateCapabilities DellStateCapabilities,
    pCIDeviceConfigurationSpaceStateSettings    DellStateSettings,
    pCIDeviceConfigurationSpaceStatus           DellStatus,
    pCIDeviceIndexReference                     DellObjectRange,
    pCIDeviceConfigurationSpaceBusNumber        DellUnsigned32BitRange,
    pCIDeviceConfigurationSpaceDeviceNumber     DellUnsigned32BitRange,
    pCIDeviceConfigurationSpaceFunctionNumber   DellUnsigned32BitRange,
    pCIDeviceConfigurationSpaceHeader           OCTET STRING(SIZE(0..1025))
}

pCIDeviceConfigurationSpaceTable                OBJECT-TYPE
    SYNTAX      SEQUENCE OF PCIDeviceConfigurationSpaceTableEntry
    ACCESS      not-accessible
    STATUS      mandatory
    DESCRIPTION
"1100.0082 This object defines the PCI Device Configuration Space Table."
    ::= { deviceGroup 82 }
pCIDeviceConfigurationSpaceTableEntry           OBJECT-TYPE
    SYNTAX      PCIDeviceConfigurationSpaceTableEntry
    ACCESS      not-accessible
    STATUS      mandatory
    DESCRIPTION
"1100.0082.0001 This object defines the PCI Device Configuration Space Table
Entry."
    INDEX       { pCIDeviceConfigurationSpacechassisIndex,
                  pCIDeviceConfigurationSpaceIndex }
    ::= { pCIDeviceConfigurationSpaceTable 1 }

pCIDeviceConfigurationSpacechassisIndex         OBJECT-TYPE
    SYNTAX      DellObjectRange
    ACCESS      read-only
    STATUS      mandatory
    DESCRIPTION
"1100.0082.0001.0001 This attribute defines the index (one based) of the
associated chassis."
    ::= { pCIDeviceConfigurationSpaceTableEntry 1 }
pCIDeviceConfigurationSpaceIndex                OBJECT-TYPE
    SYNTAX      DellObjectRange
    ACCESS      read-only
    STATUS      mandatory
    DESCRIPTION
"1100.0082.0001.0002 This attribute defines the index (one based) of the
PCI device configuration space."
    ::= { pCIDeviceConfigurationSpaceTableEntry 2 }
pCIDeviceConfigurationSpaceStateCapabilities    OBJECT-TYPE
    SYNTAX      DellStateCapabilities
    ACCESS      read-only
    STATUS      mandatory
    DESCRIPTION
"1100.0082.0001.0003 This attribute defines the state capabilities of the
PCI device configuration space."
    ::= { pCIDeviceConfigurationSpaceTableEntry 3 }
pCIDeviceConfigurationSpaceStateSettings        OBJECT-TYPE
    SYNTAX      DellStateSettings
    ACCESS      read-write
    STATUS      mandatory
    DESCRIPTION
"1100.0082.0001.0004 This attribute defines the state settings of the
PCI device configuration space."
    ::= { pCIDeviceConfigurationSpaceTableEntry 4 }
pCIDeviceConfigurationSpaceStatus               OBJECT-TYPE
    SYNTAX      DellStatus
    ACCESS      read-only
    STATUS      mandatory
    DESCRIPTION
"1100.0082.0001.0005 This attribute defines the status of the
PCI device configuration space."
    ::= { pCIDeviceConfigurationSpaceTableEntry 5 }
pCIDeviceIndexReference                         OBJECT-TYPE
    SYNTAX      DellObjectRange
    ACCESS      read-only
    STATUS      mandatory
    DESCRIPTION
"1100.0082.0001.0006 This attribute defines the index (one based) of the
PCI device that this PCI device configuration space applies to."
    ::= { pCIDeviceConfigurationSpaceTableEntry 6 }
pCIDeviceConfigurationSpaceBusNumber            OBJECT-TYPE
    SYNTAX      DellUnsigned32BitRange
    ACCESS      read-only
    STATUS      mandatory
    DESCRIPTION
"1100.0082.0001.0007 This attribute defines the bus number of the
PCI device configuration space."
    ::= { pCIDeviceConfigurationSpaceTableEntry 7 }
pCIDeviceConfigurationSpaceDeviceNumber         OBJECT-TYPE
    SYNTAX      DellUnsigned32BitRange
    ACCESS      read-only
    STATUS      mandatory
    DESCRIPTION
"1100.0082.0001.0008 This attribute defines the device number of the
PCI device configuration space."
    ::= { pCIDeviceConfigurationSpaceTableEntry 8 }
pCIDeviceConfigurationSpaceFunctionNumber       OBJECT-TYPE
    SYNTAX      DellUnsigned32BitRange
    ACCESS      read-only
    STATUS      mandatory
    DESCRIPTION
"1100.0082.0001.0009 This attribute defines the function number of the
PCI device configuration space."
    ::= { pCIDeviceConfigurationSpaceTableEntry 9 }
pCIDeviceConfigurationSpaceHeader               OBJECT-TYPE
    SYNTAX      OCTET STRING(SIZE(0..1025))
    ACCESS      read-only
    STATUS      mandatory
    DESCRIPTION
"1100.0082.0001.0010 This attribute defines the header of the
PCI device configuration space."
    ::= { pCIDeviceConfigurationSpaceTableEntry 10 }


-------------------------------------------------------------------------------
-- Network Device Table
--
-- OID Format: 1.3.6.1.4.1.674.10892.1.1100.90.1.<a>.<i1>.<i2>
-------------------------------------------------------------------------------

DellNetworkDeviceConnectionStatus               ::= INTEGER {
    -- unknown(0),                              -  unable to determine connection status
    connected(1),                               -- media reports connected
    disconnected(2),                            -- media reports disconnected
    driverBad(3),                               -- driver cannot be opened to determine status
    driverDisabled(4),                          -- driver is disabled
    hardwareInitalizing(10),                    -- hardware is initializing
    hardwareResetting(11),                      -- hardware is resetting
    hardwareClosing(12),                        -- hardware is closing down
    hardwareNotReady(13)                        -- hardware is not ready
}
DellNetworkDeviceTeamingFlags                   ::= INTEGER {
    -- Note: These values are bit fields, so combination values are possible.
    -- undefined(0),                            -  teaming flags are undefined
    noTeam(1),                                  -- device is not part of any team
    teamingEnabled(2),                          -- teaming is enabled
    adapterFaultToleranceMode(4),               -- adapter fault tolerance teaming mode
    loadBalancingMode(8)                        -- load balancing teaming mode
}
DellNetworkDeviceTOECapabilityFlags             ::= INTEGER {
    -- Note: These values are bit fields, so combination values are possible.
    -- none(0),                                 -  querying for TOE capability is not supported
    unknown(1),                                 -- querying for TOE capability is supported but query returned an error
    available(2),                               -- device has TOE capability
    notAvailable(4),                            -- device does not have TOE capability
    cannotBeDetermined(8),                      -- querying for TOE capability is supported but an error prevented querying
    driverNotResponding(16)                     -- querying for TOE capability is supported but driver did not respond to query
}
DellNetworkDeviceRDMACapabilityFlags            ::= INTEGER {
    -- Note: These values are bit fields, so combination values are possible.
    -- none(0),                                 -  querying for RDMA capability is not supported
    unknown(1),                                 -- querying for RDMA capability is supported but query returned an error
    available(2),                               -- device has RDMA capability
    notAvailable(4),                            -- device does not have RDMA capability
    cannotBeDetermined(8),                      -- querying for RDMA capability is supported but an error prevented querying
    driverNotResponding(16)                     -- querying for RDMA capability is supported but driver did not respond to query
}
DellNetworkDeviceiSCSICapabilityFlags           ::= INTEGER {
    -- Note: These values are bit fields, so combination values are possible.
    -- none(0),                                 -  querying for iSCSI capability is not supported
    unknown(1),                                 -- querying for iSCSI capability is supported but query returned an error
    available(2),                               -- device has iSCSI capability
    notAvailable(4),                            -- device does not have iSCSI capability
    cannotBeDetermined(8),                      -- querying for iSCSI capability is supported but an error prevented querying
    driverNotResponding(16)                     -- querying for iSCSI capability is supported but driver did not respond to query
}
DellNetworkDeviceCapabilities                   ::= INTEGER {
    -- Note: These values are bit fields, so combination values are possible.
    -- notSupported(0),                         -  device does not support reporting capabilities via this attribute
    supported(1),                               -- device supports reporting capabilities via this attribute
    toe(2),                                     -- device has TOE capability
    iscsiOffload(4),                            -- device has iSCSI Offload capability
    fcoeOffload(8)                              -- device has FCoE Offload capability
}

NetworkDeviceTableEntry                         ::= SEQUENCE {
    networkDeviceChassisIndex                   DellObjectRange,
    networkDeviceIndex                          DellObjectRange,
    networkDeviceStatus                         DellStatus,
    networkDeviceConnectionStatus               DellNetworkDeviceConnectionStatus,
    networkDeviceDescriptionName                DellString,
    networkDeviceProductName                    DellString,
    networkDeviceVendorName                     DellString,
    networkDeviceServiceName                    DellString,
    networkDeviceDriverImagePathName            DellString,
    networkDeviceDriverVersionName              DellString,
    networkDeviceIPAddress                      IpAddress,
    networkDeviceIPSubnetMask                   IpAddress,
    networkDeviceDefaultGatewayIPAddress        IpAddress,
    networkDeviceDHCPServerIPAddress            IpAddress,
    networkDeviceCurrentMACAddress              DellMACAddress,
    networkDevicePermanentMACAddress            DellMACAddress,
    networkDevicePCIBusNumber                   DellUnsigned8BitRange,
    networkDevicePCIDeviceNumber                DellUnsigned8BitRange,
    networkDevicePCIFunctionNumber              DellUnsigned8BitRange,
    networkDeviceIRQ                            DellUnsigned32BitRange,
    networkDeviceBaseIOPortAddress              DellUnsigned32BitRange,
    networkDeviceTeamingFlags                   DellNetworkDeviceTeamingFlags,
    networkDeviceTOECapabilityFlags             DellNetworkDeviceTOECapabilityFlags,
    networkDeviceTOEEnabled                     DellBoolean,
    networkDeviceRDMACapabilityFlags            DellNetworkDeviceRDMACapabilityFlags,
    networkDeviceRDMAEnabled                    DellBoolean,
    networkDeviceiSCSICapabilityFlags           DellNetworkDeviceiSCSICapabilityFlags,
    networkDeviceiSCSIEnabled                   DellBoolean,
    networkDeviceCapabilities                   DellNetworkDeviceCapabilities
}

networkDeviceTable                              OBJECT-TYPE
    SYNTAX      SEQUENCE OF NetworkDeviceTableEntry
    ACCESS      not-accessible
    STATUS      mandatory
    DESCRIPTION
"1100.0090 This object defines the Network Device Table."
    ::= { deviceGroup 90 }
networkDeviceTableEntry                         OBJECT-TYPE
    SYNTAX      NetworkDeviceTableEntry
    ACCESS      not-accessible
    STATUS      mandatory
    DESCRIPTION
"1100.0090.0001 This object defines the Network Device Table Entry."
    INDEX       { networkDeviceChassisIndex,
                  networkDeviceIndex }
    ::= { networkDeviceTable 1 }

networkDeviceChassisIndex                       OBJECT-TYPE
    SYNTAX      DellObjectRange
    ACCESS      read-only
    STATUS      mandatory
    DESCRIPTION
"1100.0090.0001.0001 This attribute defines the index (one based) of the
chassis that contains the network device."
    ::= { networkDeviceTableEntry 1 }
networkDeviceIndex                              OBJECT-TYPE
    SYNTAX      DellObjectRange
    ACCESS      read-only
    STATUS      mandatory
    DESCRIPTION
"1100.0090.0001.0002 This attribute defines the index (one based) of the
network device."
    ::= { networkDeviceTableEntry 2 }
networkDeviceStatus                             OBJECT-TYPE
    SYNTAX      DellStatus
    ACCESS      read-only
    STATUS      mandatory
    DESCRIPTION
"1100.0090.0001.0003 This attribute defines the status of the network device."
    ::= { networkDeviceTableEntry 3 }
networkDeviceConnectionStatus                   OBJECT-TYPE
    SYNTAX      DellNetworkDeviceConnectionStatus
    ACCESS      read-only
    STATUS      mandatory
    DESCRIPTION
"1100.0090.0001.0004 This attribute defines the connection status of the
network device."
    ::= { networkDeviceTableEntry 4 }
networkDeviceDescriptionName                    OBJECT-TYPE
    SYNTAX      DellString
    ACCESS      read-only
    STATUS      mandatory
    DESCRIPTION
"1100.0090.0001.0005 This attribute defines the description of the
network device."
    ::= { networkDeviceTableEntry 5 }
networkDeviceProductName                        OBJECT-TYPE
    SYNTAX      DellString
    ACCESS      read-only
    STATUS      mandatory
    DESCRIPTION
"1100.0090.0001.0006 This attribute defines the product name of the
network device."
    ::= { networkDeviceTableEntry 6 }
networkDeviceVendorName                         OBJECT-TYPE
    SYNTAX      DellString
    ACCESS      read-only
    STATUS      mandatory
    DESCRIPTION
"1100.0090.0001.0007 This attribute defines the name of the vendor of the
network device."
    ::= { networkDeviceTableEntry 7 }
networkDeviceServiceName                        OBJECT-TYPE
    SYNTAX      DellString
    ACCESS      read-only
    STATUS      mandatory
    DESCRIPTION
"1100.0090.0001.0008 This attribute defines the service name of the
network device."
    ::= { networkDeviceTableEntry 8 }
networkDeviceDriverImagePathName                OBJECT-TYPE
    SYNTAX      DellString
    ACCESS      read-only
    STATUS      mandatory
    DESCRIPTION
"1100.0090.0001.0009 This attribute defines the path to the binary image
of the driver for the network device."
    ::= { networkDeviceTableEntry 9 }
networkDeviceDriverVersionName                  OBJECT-TYPE
    SYNTAX      DellString
    ACCESS      read-only
    STATUS      mandatory
    DESCRIPTION
"1100.0090.0001.0010 This attribute defines the version of the driver
for the network device."
    ::= { networkDeviceTableEntry 10 }
networkDeviceIPAddress                          OBJECT-TYPE
    SYNTAX      IpAddress
    ACCESS      read-only
    STATUS      mandatory
    DESCRIPTION
"1100.0090.0001.0011 This attribute defines the IP address of the
network device."
    ::= { networkDeviceTableEntry 11 }
networkDeviceIPSubnetMask                       OBJECT-TYPE
    SYNTAX      IpAddress
    ACCESS      read-only
    STATUS      mandatory
    DESCRIPTION
"1100.0090.0001.0012 This attribute defines the IP subnet mask for the
IP address currently assigned to the network device."
    ::= { networkDeviceTableEntry 12 }
networkDeviceDefaultGatewayIPAddress            OBJECT-TYPE
    SYNTAX      IpAddress
    ACCESS      read-only
    STATUS      mandatory
    DESCRIPTION
"1100.0090.0001.0013 This attribute defines the IP address of the
default gateway for the network device."
    ::= { networkDeviceTableEntry 13 }
networkDeviceDHCPServerIPAddress                OBJECT-TYPE
    SYNTAX      IpAddress
    ACCESS      read-only
    STATUS      mandatory
    DESCRIPTION
"1100.0090.0001.0014 This attribute defines the IP address of the
DHCP server that was used to obtain the IP address of the network device
if DHCP is used to configure the network device."
    ::= { networkDeviceTableEntry 14 }
networkDeviceCurrentMACAddress                  OBJECT-TYPE
    SYNTAX      DellMACAddress
    ACCESS      read-only
    STATUS      mandatory
    DESCRIPTION
"1100.0090.0001.0015 This attribute defines the current MAC address of the
network device."
    ::= { networkDeviceTableEntry 15 }
networkDevicePermanentMACAddress                OBJECT-TYPE
    SYNTAX      DellMACAddress
    ACCESS      read-only
    STATUS      mandatory
    DESCRIPTION
"1100.0090.0001.0016 This attribute defines the permanent MAC address of the
network device."
    ::= { networkDeviceTableEntry 16 }
networkDevicePCIBusNumber                       OBJECT-TYPE
    SYNTAX      DellUnsigned8BitRange
    ACCESS      read-only
    STATUS      mandatory
    DESCRIPTION
"1100.0090.0001.0017 This attribute defines the PCI bus number of the
network device."
    ::= { networkDeviceTableEntry 17 }
networkDevicePCIDeviceNumber                    OBJECT-TYPE
    SYNTAX      DellUnsigned8BitRange
    ACCESS      read-only
    STATUS      mandatory
    DESCRIPTION
"1100.0090.0001.0018 This attribute defines the PCI device number of the
network device."
    ::= { networkDeviceTableEntry 18 }
networkDevicePCIFunctionNumber                  OBJECT-TYPE
    SYNTAX      DellUnsigned8BitRange
    ACCESS      read-only
    STATUS      mandatory
    DESCRIPTION
"1100.0090.0001.0019 This attribute defines the PCI function number of the
network device."
    ::= { networkDeviceTableEntry 19 }
networkDeviceIRQ                                OBJECT-TYPE
    SYNTAX      DellUnsigned32BitRange
    ACCESS      read-only
    STATUS      mandatory
    DESCRIPTION
"1100.0090.0001.0020 This attribute defines the interrupt request number
of the network device."
    ::= { networkDeviceTableEntry 20 }
networkDeviceBaseIOPortAddress                  OBJECT-TYPE
    SYNTAX      DellUnsigned32BitRange
    ACCESS      read-only
    STATUS      mandatory
    DESCRIPTION
"1100.0090.0001.0021 This attribute defines the base input/outport port
address of the network device."
    ::= { networkDeviceTableEntry 21 }
networkDeviceTeamingFlags                       OBJECT-TYPE
    SYNTAX      DellNetworkDeviceTeamingFlags
    ACCESS      read-only
    STATUS      mandatory
    DESCRIPTION
"1100.0090.0001.0022 This attribute defines the teaming features of the
network device."
    ::= { networkDeviceTableEntry 22 }
networkDeviceTOECapabilityFlags                 OBJECT-TYPE
    SYNTAX      DellNetworkDeviceTOECapabilityFlags
    ACCESS      read-only
    STATUS      mandatory
    DESCRIPTION
"1100.0090.0001.0023 This attribute defines the TCP/IP Offload Engine (TOE)
capability flags of the network device."
    ::= { networkDeviceTableEntry 23 }
networkDeviceTOEEnabled                         OBJECT-TYPE
    SYNTAX      DellBoolean
    ACCESS      read-only
    STATUS      mandatory
    DESCRIPTION
"1100.0090.0001.0024 This attribute defines if TOE is enabled for the
network device."
    ::= { networkDeviceTableEntry 24 }
networkDeviceRDMACapabilityFlags                OBJECT-TYPE
    SYNTAX      DellNetworkDeviceRDMACapabilityFlags
    ACCESS      read-only
    STATUS      mandatory
    DESCRIPTION
"1100.0090.0001.0025 This attribute defines the Remote Direct Memory Access
(RDMA) capability flags of the network device."
    ::= { networkDeviceTableEntry 25 }
networkDeviceRDMAEnabled                        OBJECT-TYPE
    SYNTAX      DellBoolean
    ACCESS      read-only
    STATUS      mandatory
    DESCRIPTION
"1100.0090.0001.0026 This attribute defines if RDMA is enabled for the
network device."
    ::= { networkDeviceTableEntry 26 }
networkDeviceiSCSICapabilityFlags               OBJECT-TYPE
    SYNTAX      DellNetworkDeviceiSCSICapabilityFlags
    ACCESS      read-only
    STATUS      mandatory
    DESCRIPTION
"1100.0090.0001.0027 This attribute defines the Internet Small Computer
System Interface (iSCSI) capability flags of the network device."
    ::= { networkDeviceTableEntry 27 }
networkDeviceiSCSIEnabled                       OBJECT-TYPE
    SYNTAX      DellBoolean
    ACCESS      read-only
    STATUS      mandatory
    DESCRIPTION
"1100.0090.0001.0028 This attribute defines if iSCSI is enabled for the
network device."
    ::= { networkDeviceTableEntry 28 }
networkDeviceCapabilities                       OBJECT-TYPE
    SYNTAX      DellNetworkDeviceCapabilities
    ACCESS      read-only
    STATUS      mandatory
    DESCRIPTION
"1100.0090.0001.0029 This attribute defines the capabilities of the network device.
If this value is notSupported(0), the networkDeviceTOECapabilityFlags,
networkDeviceTOEEnabled, networkDeviceRDMACapabilityFlags, networkDeviceRDMAEnabled,
networkDeviceiSCSICapabilityFlags and networkDeviceiSCSIEnabled attributes should
be used to determine the network device capabilities.  If the supported(1) bit
is on, this attribute should be used to determine the network device capabilities,
and the attributes mentioned above should not be used.  NOTE: For a network device
on Converged Network Adapter (CNA), this attribute provides capability information
for the CNA and not for the network device. For more information read vendor
documentation."
    ::= { networkDeviceTableEntry 29 }


-------------------------------------------------------------------------------
-- Managed System Services Device Table
--
-- OID Format: 1.3.6.1.4.1.674.10892.1.1100.100.1.<a>.<i1>.<i2>
-------------------------------------------------------------------------------

DellManagedSystemServicesDeviceType             ::= INTEGER {
    -- baseDevice(0),                           -  type is base device
    optionalDevice(1)                           -- type is optional device
}

ManagedSystemServicesDeviceTableEntry           ::= SEQUENCE {
    managedSystemServicesDeviceChassisIndex     DellObjectRange,
    managedSystemServicesDeviceIndex            DellObjectRange,
    managedSystemServicesDeviceStatus           DellStatus,
    managedSystemServicesDeviceType             DellManagedSystemServicesDeviceType,
    managedSystemServicesDeviceStoragePresent   DellBoolean,
    managedSystemServicesDeviceStorageSize      DellUnsigned32BitRange
}

managedSystemServicesDeviceTable                OBJECT-TYPE
    SYNTAX      SEQUENCE OF ManagedSystemServicesDeviceTableEntry
    ACCESS      not-accessible
    STATUS      mandatory
    DESCRIPTION
"1100.0100 This object defines the Managed System Services Device Table."
    ::= { deviceGroup 100 }
managedSystemServicesDeviceTableEntry           OBJECT-TYPE
    SYNTAX      ManagedSystemServicesDeviceTableEntry
    ACCESS      not-accessible
    STATUS      mandatory
    DESCRIPTION
"1100.0100.0001 This object defines the Managed System Services Device Table
Entry."
    INDEX       { managedSystemServicesDeviceChassisIndex,
                  managedSystemServicesDeviceIndex }
    ::= { managedSystemServicesDeviceTable 1 }

managedSystemServicesDeviceChassisIndex         OBJECT-TYPE
    SYNTAX      DellObjectRange
    ACCESS      read-only
    STATUS      mandatory
    DESCRIPTION
"1100.0100.0001.0001 This attribute defines the index (one-based) of the
chassis that contains the managed system services device."
    ::= { managedSystemServicesDeviceTableEntry 1 }
managedSystemServicesDeviceIndex                OBJECT-TYPE
    SYNTAX      DellObjectRange
    ACCESS      read-only
    STATUS      mandatory
    DESCRIPTION
"1100.0100.0001.0002 This attribute defines the index (one-based) of the
managed system services device."
    ::= { managedSystemServicesDeviceTableEntry 2 }
managedSystemServicesDeviceStatus               OBJECT-TYPE
    SYNTAX      DellStatus
    ACCESS      read-only
    STATUS      mandatory
    DESCRIPTION
"1100.0100.0001.0003 This attribute defines the status of the
managed system services device."
    ::= { managedSystemServicesDeviceTableEntry 3 }
managedSystemServicesDeviceType                 OBJECT-TYPE
    SYNTAX      DellManagedSystemServicesDeviceType
    ACCESS      read-only
    STATUS      mandatory
    DESCRIPTION
"1100.0100.0001.0004 This attribute defines the type of the
managed system services device."
    ::= { managedSystemServicesDeviceTableEntry 4 }
managedSystemServicesDeviceStoragePresent       OBJECT-TYPE
    SYNTAX      DellBoolean
    ACCESS      read-only
    STATUS      mandatory
    DESCRIPTION
"1100.0100.0001.0005 This attribute defines whether storage is present
on the managed system services device."
    ::= { managedSystemServicesDeviceTableEntry 5 }
managedSystemServicesDeviceStorageSize          OBJECT-TYPE
    SYNTAX      DellUnsigned32BitRange
    ACCESS      read-only
    STATUS      mandatory
    DESCRIPTION
"1100.0100.0001.0006 This attribute defines the size in MB (megabytes)
of the storage present on the managed system services device."
    ::= { managedSystemServicesDeviceTableEntry 6 }


-------------------------------------------------------------------------------
-- SD Card Unit Table
--
-- OID Format: 1.3.6.1.4.1.674.10892.1.1100.110.1.<a>.<i1>.<i2>
-------------------------------------------------------------------------------

SdCardUnitTableEntry                            ::= SEQUENCE {
    sdCardUnitChassisIndex                      DellObjectRange,
    sdCardUnitIndex                             DellObjectRange,
    sdCardUnitStateCapabilities                 DellStateCapabilities,
    sdCardUnitStateSettings                     DellStateSettings,
    sdCardUnitRedundancyStatus                  DellStatusRedundancy,
    sdCardUnitCountForRedundancy                DellObjectRange,
    sdCardUnitName                              DellString,
    sdCardUnitStatus                            DellStatus
}

sdCardUnitTable                                 OBJECT-TYPE
    SYNTAX      SEQUENCE OF SdCardUnitTableEntry
    ACCESS      not-accessible
    STATUS      mandatory
    DESCRIPTION
"1100.0110 This object defines the SD Card Unit Table."
    ::= { deviceGroup 110 }
sdCardUnitTableEntry                            OBJECT-TYPE
    SYNTAX      SdCardUnitTableEntry
    ACCESS      not-accessible
    STATUS      mandatory
    DESCRIPTION
"1100.0110.0001 This object defines the SD Card Unit Table Entry."
    INDEX       { sdCardUnitChassisIndex,
                  sdCardUnitIndex }
    ::= { sdCardUnitTable 1 }

sdCardUnitChassisIndex                          OBJECT-TYPE
    SYNTAX      DellObjectRange
    ACCESS      read-only
    STATUS      mandatory
    DESCRIPTION
"1100.0110.0001.0001 This attribute defines the index (one-based) of the
chassis that contains the SD Card unit."
    ::= { sdCardUnitTableEntry 1 }
sdCardUnitIndex                                 OBJECT-TYPE
    SYNTAX      DellObjectRange
    ACCESS      read-only
    STATUS      mandatory
    DESCRIPTION
"1100.0110.0001.0002 This attribute defines the index (one-based) of the
SD Card unit."
    ::= { sdCardUnitTableEntry 2 }
sdCardUnitStateCapabilities                     OBJECT-TYPE
    SYNTAX      DellStateCapabilities
    ACCESS      read-only
    STATUS      mandatory
    DESCRIPTION
"1100.0110.0001.0003 This attribute defines the state capabilities of the
SD Card unit."
    ::= { sdCardUnitTableEntry 3 }
sdCardUnitStateSettings                         OBJECT-TYPE
    SYNTAX      DellStateSettings
    ACCESS      read-only
    STATUS      mandatory
    DESCRIPTION
"1100.0110.0001.0004 This attribute defines the state settings of the
SD Card unit."
    ::= { sdCardUnitTableEntry 4 }
sdCardUnitRedundancyStatus                      OBJECT-TYPE
    SYNTAX      DellStatusRedundancy
    ACCESS      read-only
    STATUS      mandatory
    DESCRIPTION
"1100.0110.0001.0005 This attribute defines the redundancy status of the
SD Card unit."
    ::= { sdCardUnitTableEntry 5 }
sdCardUnitCountForRedundancy                    OBJECT-TYPE
    SYNTAX      DellObjectRange
    ACCESS      read-only
    STATUS      mandatory
    DESCRIPTION
"1100.0110.0001.0006 This attribute defines the total number of SD Card
devices required for this SD Card unit to have full redundancy."
    ::= { sdCardUnitTableEntry 6 }
sdCardUnitName                                  OBJECT-TYPE
    SYNTAX      DellString
    ACCESS      read-only
    STATUS      mandatory
    DESCRIPTION
"1100.0110.0001.0007 This attribute defines the name of the SD Card unit."
    ::= { sdCardUnitTableEntry 7 }
sdCardUnitStatus                                OBJECT-TYPE
    SYNTAX      DellStatus
    ACCESS      read-only
    STATUS      mandatory
    DESCRIPTION
"1100.0110.0001.0008 This attribute defines the status of the SD Card unit."
    ::= { sdCardUnitTableEntry 8 }


-------------------------------------------------------------------------------
-- SD Card Device Table
--
-- OID Format: 1.3.6.1.4.1.674.10892.1.1100.112.1.<a>.<i1>.<i2>
-------------------------------------------------------------------------------

DellSDCardDeviceType                            ::= INTEGER {
    other(1),                                   -- device type is other
    unknown(2),                                 -- device type is unknown
    hypervisor(3),                              -- device type is Hypervisor
    vFlash(4)                                   -- device type is Virtual Flash (vFlash)
}
DellSDCardDeviceConfigCapabilities              ::= INTEGER {
    -- Note: These values are bit fields, so combination values are possible.
    -- none(0),                                 -  no capabilities
    sdCapable(1),                               -- SD media can be enabled
    vFlashCapable(2)                            -- vFlash can be enabled
}
DellSDCardDeviceConfigSettings                  ::= INTEGER {
    -- Note: These values are bit fields, so combination values are possible.
    -- none(0),                                 -  no settings enabled
    sdEnabled(1),                               -- SD media enabled
    vFlashEnabled(2)                            -- vFlash enabled
}
DellSDCardDeviceCardState                       ::= INTEGER {
    -- Note: These values are bit fields, so combination values are possible.
    -- none(0),                                 -  state is none of the following:
    present(1),                                 -- device is present
    ipmiReady(2),                               -- device is IPMI ready
    fullReady(4),                               -- device is full ready
    offline(8),                                 -- device is offline
    failed(16),                                 -- device is failed
    active(32),                                 -- device is active
    bootable(64),                               -- device is bootable
    writeProtect(128),                          -- device is write-protected
    standby(256)                                -- device is in standby mode
}
DellSDCardDeviceCardLicensed                    ::= INTEGER {
    -- unlicensed(0),                           -  SD card is not licensed by system vendor
    licensed(1)                                 -- SD card is licensed by system vendor
}

SdCardDeviceTableEntry                          ::= SEQUENCE {
    sdCardDeviceChassisIndex                    DellObjectRange,
    sdCardDeviceIndex                           DellObjectRange,
    sdCardDeviceStatus                          DellStatus,
    sdCardDeviceType                            DellSDCardDeviceType,
    sdCardDeviceConfigCapabilities              DellSDCardDeviceConfigCapabilities,
    sdCardDeviceConfigSettings                  DellSDCardDeviceConfigSettings,
    sdCardDeviceLocationName                    DellString,
    sdCardDeviceCardPresent                     DellBoolean,
    sdCardDeviceCardState                       DellSDCardDeviceCardState,
    sdCardDeviceCardStorageSize                 DellUnsigned32BitRange,
    sdCardDeviceUnitIndexReference              DellObjectRange,
    sdCardDeviceCardAvailableStorageSize        DellSigned32BitRange,
    sdCardDeviceCardLicensed                    DellSDCardDeviceCardLicensed
}

sdCardDeviceTable                               OBJECT-TYPE
    SYNTAX      SEQUENCE OF SdCardDeviceTableEntry
    ACCESS      not-accessible
    STATUS      mandatory
    DESCRIPTION
"1100.0112 This object defines the SD Card Device Table."
    ::= { deviceGroup 112 }
sdCardDeviceTableEntry                          OBJECT-TYPE
    SYNTAX      SdCardDeviceTableEntry
    ACCESS      not-accessible
    STATUS      mandatory
    DESCRIPTION
"1100.0112.0001 This object defines the SD Card Device Table Entry."
    INDEX       { sdCardDeviceChassisIndex,
                  sdCardDeviceIndex }
    ::= { sdCardDeviceTable 1 }

sdCardDeviceChassisIndex                        OBJECT-TYPE
    SYNTAX      DellObjectRange
    ACCESS      read-only
    STATUS      mandatory
    DESCRIPTION
"1100.0112.0001.0001 This attribute defines the index (one-based) of the
chassis that contains the SD Card device."
    ::= { sdCardDeviceTableEntry 1 }
sdCardDeviceIndex                               OBJECT-TYPE
    SYNTAX      DellObjectRange
    ACCESS      read-only
    STATUS      mandatory
    DESCRIPTION
"1100.0112.0001.0002 This attribute defines the index (one-based) of the
SD Card device."
    ::= { sdCardDeviceTableEntry 2 }
sdCardDeviceStatus                              OBJECT-TYPE
    SYNTAX      DellStatus
    ACCESS      read-only
    STATUS      mandatory
    DESCRIPTION
"1100.0112.0001.0003 This attribute defines the status of the SD Card device."
    ::= { sdCardDeviceTableEntry 3 }
sdCardDeviceType                                OBJECT-TYPE
    SYNTAX      DellSDCardDeviceType
    ACCESS      read-only
    STATUS      mandatory
    DESCRIPTION
"1100.0112.0001.0004 This attribute defines the type of the SD Card device."
    ::= { sdCardDeviceTableEntry 4 }
sdCardDeviceConfigCapabilities                  OBJECT-TYPE
    SYNTAX      DellSDCardDeviceConfigCapabilities
    ACCESS      read-only
    STATUS      mandatory
    DESCRIPTION
"1100.0112.0001.0005 This attribute defines the configuration capabilities
of the SD Card device."
    ::= { sdCardDeviceTableEntry 5 }
sdCardDeviceConfigSettings                      OBJECT-TYPE
    SYNTAX      DellSDCardDeviceConfigSettings
    ACCESS      read-only
    STATUS      mandatory
    DESCRIPTION
"1100.0112.0001.0006 This attribute defines the configuration settings
of the SD Card device."
    ::= { sdCardDeviceTableEntry 6 }
sdCardDeviceLocationName                        OBJECT-TYPE
    SYNTAX      DellString
    ACCESS      read-only
    STATUS      mandatory
    DESCRIPTION
"1100.0112.0001.0007 This attribute defines the location of the SD Card device."
    ::= { sdCardDeviceTableEntry 7 }
sdCardDeviceCardPresent                         OBJECT-TYPE
    SYNTAX      DellBoolean
    ACCESS      read-only
    STATUS      mandatory
    DESCRIPTION
"1100.0112.0001.0008 This attribute defines whether the SD card is present
for the SD Card device."
    ::= { sdCardDeviceTableEntry 8 }
sdCardDeviceCardState                           OBJECT-TYPE
    SYNTAX      DellSDCardDeviceCardState
    ACCESS      read-only
    STATUS      mandatory
    DESCRIPTION
"1100.0112.0001.0009 This attribute defines the state of the SD card."
    ::= { sdCardDeviceTableEntry 9 }
sdCardDeviceCardStorageSize                     OBJECT-TYPE
    SYNTAX      DellUnsigned32BitRange
    ACCESS      read-only
    STATUS      mandatory
    DESCRIPTION
"1100.0112.0001.0010 This attribute defines the total storage size in MB (megabytes)
of the SD card for the SD Card device."
    ::= { sdCardDeviceTableEntry 10 }
sdCardDeviceUnitIndexReference                  OBJECT-TYPE
    SYNTAX      DellObjectRange
    ACCESS      read-only
    STATUS      mandatory
    DESCRIPTION
"1100.0112.0001.0011 This attribute defines the index to the associated
SD Card unit if the SD Card device is part of a SD Card unit."
    ::= { sdCardDeviceTableEntry 11 }
sdCardDeviceCardAvailableStorageSize            OBJECT-TYPE
    SYNTAX      DellSigned32BitRange
    ACCESS      read-only
    STATUS      mandatory
    DESCRIPTION
"1100.0112.0001.0012 This attribute defines the available storage size in MB (megabytes)
of the SD card for the SD Card device."
    ::= { sdCardDeviceTableEntry 12 }
sdCardDeviceCardLicensed                        OBJECT-TYPE
    SYNTAX      DellSDCardDeviceCardLicensed
    ACCESS      read-only
    STATUS      mandatory
    DESCRIPTION
"1100.0112.0001.0013 This attribute defines whether the SD card is licensed
by the system vendor."
    ::= { sdCardDeviceTableEntry 13 }


-------------------------------------------------------------------------------
-- Slot Group
--
-- OID Format: 1.3.6.1.4.1.674.10892.1.1200
-------------------------------------------------------------------------------


-------------------------------------------------------------------------------
-- System Slot Table
--
-- OID Format: 1.3.6.1.4.1.674.10892.1.1200.10.1.<a>.<i1>.<i2>
-------------------------------------------------------------------------------

DellSystemSlotStateCapabilities                       ::= INTEGER {
    systemSlotHotPlugIsUnknown(1),              -- state capabilities are unknown
    systemSlotHotPlugIsHotPluggableCapable(2),  -- slot can support Hot Plug
    systemSlotHotPlugCanBePoweredOn(4),         -- slot power (and corresponding LED) can be powered on
    systemSlotHotPlugCanSignalAttention(8),     -- slot attention state (and corresponding LED) can be set
    systemSlotHotPlugCanSignalPowerFault(16),   -- slot power on fault (and corresponding LED) can be detected due to a short or overcurrent
    systemSlotHotPlugCanSignalAdapterPresent(32),  -- slot adapter (card) present in slot (may not be powered) can be detected
    systemSlotHotPlugCanSignalPowerButtonPressed(64),  -- slot power button can be pressed to signal a toggle of the power state
    canSupportAllHotPlugCapabilities(126),      -- slot can support all Hot Plug capabilities
    systemSlotCanProvide5Volts(128),            -- slot can provide 5 volt supply
    systemSlotCanProvide3Point3Volts(256),      -- slot can provide 3.3 volt supply
    systemSlotCanSignalIfShared(512),           -- slot opening if shared with another slot can be detected
    systemSlotCanSupportCard16(1024),           -- slot can support PC Card-16
    systemSlotCanSupportCardBus(2048),          -- slot can support CardBus
    systemSlotCanSupportZoomVideo(4096),        -- slot can support Zoom Video
    systemSlotCanSupportModemRingResume(8192),  -- slot can support Modem Ring Resume
    systemSlotCanSupportPMESignal(16384),       -- slot can support Power Management Enable (PME#) signal
    canSupportAllSlotCapabilities(32640),       -- slot can support all Slot capabilities
    canSupportAllSlotAndAllHotPlugCapabilities(32766) -- slot can support all Slot and all Hot Plug capabilities
}
DellSystemSlotStateSettings                     ::= INTEGER {
    systemSlotHotPlugIsUnknown(1),              -- state settings are unknown
    systemSlotHotPlugIsHotPluggable(2),         -- slot supports Hot Plug
    systemSlotHotPlugIsPoweredOn(4),            -- slot has power (and corresponding LED) ON
    systemSlotHotPlugIsAtAttention(8),          -- slot is at attention state (and corresponding LED) is ON
    systemSlotHotPlugHasPowerFaulted(16),       -- slot has power on fault (and corresponding LED) was detected due to a short or overcurrent
    systemSlotHotPlugAdapterIsPresent(32),      -- slot adapter (card) present in slot (may not be powered on)
    systemSlotHotPlugAdapterPresentAndPoweredOn(36),  -- slot adapter (card) present in slot and powered on
    systemSlotHotPlugPowerButtonPressed(64),    -- slot power button pressed to signal toggle of power state
    systemSlotProvides5Volts(128),              -- slot provides 5 volt supply
    systemSlotProvides3Point3Volts(256),        -- slot provides 3.3 volt supply
    systemSlotIsShared(512),                    -- slot opening is shared with another slot (e.g. PCI/EISA shared slot)
    systemSlotSupportsCard16(1024),             -- slot supports PC Card-16
    systemSlotSupportsCardBus(2048),            -- slot supports CardBus
    systemSlotSupportsZoomVideo(4096),          -- slot supports Zoom Video
    systemSlotSupportsModemRingResume(8192),    -- slot supports Modem Ring Resume
    systemSlotSupportsPMESignal(16384),         -- slot supports Power Management Enable (PME#) signal
    supportsPMEand3P3Vand5VandHotPluggable(16770),
    supportsPMEand3P3Vand5VhasAdapterOn(16804),
    supportsPMEand3P3Vand5VhasAdapterOnandisHotPluggable(16806),
    supportsPMEand3P3VIsSharedand5VhasAdapterOnandHotPlugable(17316)
}
DellSystemSlotType                              ::= INTEGER {
    systemSlotIsOther(1),                       -- type is Other
    systemSlotIsUnknown(2),                     -- type is Unknown
    systemSlotIsISA(3),                         -- type is ISA
    systemSlotIsMCA(4),                         -- type is MCA
    systemSlotIsEISA(5),                        -- type is EISA
    systemSlotIsPCI(6),                         -- type is PCI
    systemSlotIsPCMCIA(7),                      -- type is PCMCIA
    systemSlotIsVLVESA(8),                      -- type is VL-VESA
    systemSlotIsProprietary(9),                 -- type is Proprietary
    systemSlotIsProcessorCard(10),              -- type is Processor Card Slot
    systemSlotIsProprietaryMemory(11),          -- type is Proprietary Memory Card Slot
    systemSlotIsIORiserCard(12),                -- type is I/O Riser Card Slot
    systemSlotIsNuBUS(13),                      -- type is NuBus
    systemSlotIsPCI66MHz(14),                   -- type is PCI - 66MHz Capable
    systemSlotIsAGP(15),                        -- type is AGP
    systemSlotIsAGP2X(16),                      -- type is AGP 2X
    systemSlotIsAGP4X(17),                      -- type is AGP 4X
    systemSlotIsPC98C20(18),                    -- type is PC-98/C20
    systemSlotIsPC98C24(19),                    -- type is PC-98/C24
    systemSlotIsPC98E(20),                      -- type is PC-98/E
    systemSlotIsPC98LocalBus(21),               -- type is PC-98/Local Bus
    systemSlotIsPC98Card(22),                   -- type is PC-98/Card
    systemSlotIsPCIX(23),                       -- type is PCI-X
    systemSlotIsPCIExpress(24),                 -- type is PCI Express
    systemSlotIsAGP8X(25),                      -- type is AGP 8X
    systemSlotIsPCIExpressX1(166),              -- type is PCI Express x1
    systemSlotIsPCIExpressX2(167),              -- type is PCI Express x2
    systemSlotIsPCIExpressX4(168),              -- type is PCI Express x4
    systemSlotIsPCIExpressX8(169),              -- type is PCI Express x8
    systemSlotIsPCIExpressX16(170),             -- type is PCI Express x16
    systemSlotIsPCIExpressGen2(171),            -- type is PCI Express Gen 2
    systemSlotIsPCIExpressGen2X1(172),          -- type is PCI Express Gen 2 x1
    systemSlotIsPCIExpressGen2X2(173),          -- type is PCI Express Gen 2 x2
    systemSlotIsPCIExpressGen2X4(174),          -- type is PCI Express Gen 2 x4
    systemSlotIsPCIExpressGen2X8(175),          -- type is PCI Express Gen 2 x8
    systemSlotIsPCIExpressGen2X16(176)          -- type is PCI Express Gen 2 x16
}
DellSystemSlotUsage                             ::= INTEGER {
    systemSlotUsageIsOther(1),                  -- usage is other than following values
    systemSlotUsageIsUnknown(2),                -- usage is unknown
    systemSlotUsageIsAvailable(3),              -- usage is available
    systemSlotUsageIsInUse(4)                   -- usage is in use
}
DellSystemSlotLength                            ::= INTEGER {
    systemSlotLengthIsOther(1),                 -- length is other than following values
    systemSlotLengthIsUnknown(2),               -- length is unknown
    systemSlotLengthIsShort(3),                 -- length is Short
    systemSlotLengthIsLong(4)                   -- length is Long
}
DellSystemSlotCategory                          ::= INTEGER {
    systemSlotCategoryIsOther(1),               -- category is other than following values
    systemSlotCategoryIsUnknown(2),             -- category is unknown
    systemSlotCategoryIsBusConnector(3),        -- category is Bus Connector
    systemSlotCategoryIsPCMCIA(4),              -- category is PCMCIA
    systemSlotCategoryIsMotherboard(5)          -- category is Motherboard
}
DellSystemSlotHotPlugBusWidth                   ::= INTEGER {
-- Bus Width meanings of type "n bits" are for parallel bus such as PCI.
-- Bus Width meanings of type "nx or xn" are for serial bus such as PCI Express.
    busWidthIsOther(1),                         -- bus width is other than following values
    busWidthIsUnknown(2),                       -- bus width is unknown
    busWidthIs8bits(3),                         -- bus width is 8 bits
    busWidthIs16bits(4),                        -- bus width is 16 bits
    busWidthIs32bits(5),                        -- bus width is 32 bits
    busWidthIs64bits(6),                        -- bus width is 64 bits
    busWidthIs128bits(7),                       -- bus width is 128 bits
    busWidthIs1xOrx1(8),                        -- bus width is 1x or x1
    busWidthIs2xOrx2(9),                        -- bus width is 2x or x2
    busWidthIs4xOrx4(10),                       -- bus width is 4x or x4
    busWidthIs8xOrx8(11),                       -- bus width is 8x or x8
    busWidthIs12xOrx12(12),                     -- bus width is 12x or x12
    busWidthIs16xOrx16(13),                     -- bus width is 16x or x16
    busWidthIs32xOrx32(14)                      -- bus width is 32x or x32
}

SystemSlotTableEntry                            ::= SEQUENCE {
    systemSlotchassisIndex                      DellObjectRange,
    systemSlotIndex                             DellObjectRange,
    systemSlotStateCapabilitiesUnique           DellSystemSlotStateCapabilities,
    systemSlotStateSettingsUnique               DellSystemSlotStateSettings,
    systemSlotStatus                            DellStatus,
    systemSlotCurrentUsage                      DellSystemSlotUsage,
    systemSlotType                              DellSystemSlotType,
    systemSlotSlotExternalSlotName              DellString,
    systemSlotLength                            DellSystemSlotLength,
    systemSlotSlotID                            DellUnsigned32BitRange,
    systemSlotCategory                          DellSystemSlotCategory,
    systemSlotHotPlugBusWidth                   DellSystemSlotHotPlugBusWidth,
    systemSlotHotPlugSlotSpeed                  DellUnsigned32BitRange,
    systemSlotHotPlugAdapterSpeed               DellUnsigned32BitRange
}

systemSlotTable                                 OBJECT-TYPE
    SYNTAX      SEQUENCE OF SystemSlotTableEntry
    ACCESS      not-accessible
    STATUS      mandatory
    DESCRIPTION
"1200.0010 This object defines the System Slot Table."
    ::= { slotGroup 10 }
systemSlotTableEntry                            OBJECT-TYPE
    SYNTAX      SystemSlotTableEntry
    ACCESS      not-accessible
    STATUS      mandatory
    DESCRIPTION
"1200.0010.0001 This object defines the System Slot Table Entry."
    INDEX       { systemSlotchassisIndex,
                  systemSlotIndex }
    ::= { systemSlotTable 1 }

systemSlotchassisIndex                          OBJECT-TYPE
    SYNTAX      DellObjectRange
    ACCESS      read-only
    STATUS      mandatory
    DESCRIPTION
"1200.0010.0001.0001 This attribute defines the index (one based) of the
associated chassis."
    ::= { systemSlotTableEntry 1 }
systemSlotIndex                                 OBJECT-TYPE
    SYNTAX      DellObjectRange
    ACCESS      read-only
    STATUS      mandatory
    DESCRIPTION
"1200.0010.0001.0002 This attribute defines the index (one based) of the
system slot."
    ::= { systemSlotTableEntry 2 }
systemSlotStateCapabilitiesUnique               OBJECT-TYPE
    SYNTAX      DellSystemSlotStateCapabilities
    ACCESS      read-only
    STATUS      mandatory
    DESCRIPTION
"1200.0010.0001.0003 This attribute defines the state capabilities of the
system slot."
    ::= { systemSlotTableEntry 3 }
systemSlotStateSettingsUnique                   OBJECT-TYPE
    SYNTAX      DellSystemSlotStateSettings
    ACCESS      read-write
    STATUS      mandatory
    DESCRIPTION
"1200.0010.0001.0004 This attribute defines the state settings of the
system slot."
    ::= { systemSlotTableEntry 4 }
systemSlotStatus                                OBJECT-TYPE
    SYNTAX      DellStatus
    ACCESS      read-only
    STATUS      mandatory
    DESCRIPTION
"1200.0010.0001.0005 This attribute defines the status of the system slot."
    ::= { systemSlotTableEntry 5 }
systemSlotCurrentUsage                          OBJECT-TYPE
    SYNTAX      DellSystemSlotUsage
    ACCESS      read-only
    STATUS      mandatory
    DESCRIPTION
"1200.0010.0001.0006 This attribute defines the current usage of the
system slot."
    ::= { systemSlotTableEntry 6 }
systemSlotType                                  OBJECT-TYPE
    SYNTAX      DellSystemSlotType
    ACCESS      read-only
    STATUS      mandatory
    DESCRIPTION
"1200.0010.0001.0007 This attribute defines the type of the system slot."
    ::= { systemSlotTableEntry 7 }
systemSlotSlotExternalSlotName                  OBJECT-TYPE
    SYNTAX      DellString
    ACCESS      read-only
    STATUS      mandatory
    DESCRIPTION
"1200.0010.0001.0008 This attribute defines the name of the external
connector name of the system slot."
    ::= { systemSlotTableEntry 8 }
systemSlotLength                                OBJECT-TYPE
    SYNTAX      DellSystemSlotLength
    ACCESS      read-only
    STATUS      mandatory
    DESCRIPTION
"1200.0010.0001.0009 This attribute defines the length of the system slot."
    ::= { systemSlotTableEntry 9 }
systemSlotSlotID                                OBJECT-TYPE
    SYNTAX      DellUnsigned32BitRange
    ACCESS      read-only
    STATUS      mandatory
    DESCRIPTION
"1200.0010.0001.0010 This attribute defines the slot identification number
of the system slot."
    ::= { systemSlotTableEntry 10 }
systemSlotCategory                              OBJECT-TYPE
    SYNTAX      DellSystemSlotCategory
    ACCESS      read-only
    STATUS      mandatory
    DESCRIPTION
"1200.0010.0001.0011 This attribute defines the category of the system slot."
    ::= { systemSlotTableEntry 11 }
systemSlotHotPlugBusWidth                       OBJECT-TYPE
    SYNTAX      DellSystemSlotHotPlugBusWidth
    ACCESS      read-only
    STATUS      mandatory
    DESCRIPTION
"1200.0010.0001.0012 This attribute defines the bus width of the hot plug
system slot."
    ::= { systemSlotTableEntry 12 }
systemSlotHotPlugSlotSpeed                      OBJECT-TYPE
    SYNTAX      DellUnsigned32BitRange
    ACCESS      read-only
    STATUS      mandatory
    DESCRIPTION
"1200.0010.0001.0013 This attribute defines the slot speed in MHz of the
hot plug system slot.  Zero indicates the slot speed is unknown."
    ::= { systemSlotTableEntry 13 }
systemSlotHotPlugAdapterSpeed                   OBJECT-TYPE
    SYNTAX      DellUnsigned32BitRange
    ACCESS      read-only
    STATUS      mandatory
    DESCRIPTION
"1200.0010.0001.0014 This attribute defines the adapter speed in MHz of the
hot plug system slot.  Zero indicates the adapter speed is unknown."
    ::= { systemSlotTableEntry 14 }


-------------------------------------------------------------------------------
-- Memory Group
--
-- OID Format: 1.3.6.1.4.1.674.10892.1.1300
-------------------------------------------------------------------------------


-------------------------------------------------------------------------------
-- Physical Memory Array Table
--
-- OID Format: 1.3.6.1.4.1.674.10892.1.1300.10.1.<a>.<i1>.<i2>
-------------------------------------------------------------------------------

DellPhysicalMemoryArrayLocation                 ::= INTEGER {
    memoryArrayLocationIsOther(1),              -- location is other than following values
    memoryArrayLocationIsUnknown(2),            -- location is unknown
    memoryArrayLocationIsSystemOrMotherboard(3),-- location is System Board or Motherboard
    memoryArrayLocationIsISA(4),                -- location is ISA add-on card
    memoryArrayLocationIsEISA(5),               -- location is EISA add-on card
    memoryArrayLocationIsPCI(6),                -- location is PCI add-on card
    memoryArrayLocationIsMCA(7),                -- location is MCA add-on card
    memoryArrayLocationIsPCMCIA(8),             -- location is PCMCIA add-on card
    memoryArrayLocationIsProprietary(9),        -- location is Proprietary add-on card
    memoryArrayLocationIsNUBUS(10),             -- location is NUBUS bus
    memoryArrayLocationIsPC98C20(11),           -- location is PC-98/C20 add-on card
    memoryArrayLocationIsPC98C24(12),           -- location is PC-98/C24 add-on card
    memoryArrayLocationIsPC98E(13),             -- location is PC-98/E add-on card
    memoryArrayLocationIsPC98LocalBus(14),      -- location is PC-98/Local Bus add-on card
    memoryArrayLocationIsPC98Card(15)           -- location is PC-98/Card slot add-on card
}
DellPhysicalMemoryArrayUse                      ::= INTEGER {
    memoryArrayUseIsOther(1),                   -- use is other than following values
    memoryArrayUseIsUnknown(2),                 -- use is unknown
    memoryArrayUseIsSystemMemory(3),            -- use is System Memory
    memoryArrayUseIsVideoMemory(4),             -- use is Video Memory
    memoryArrayUseIsFLASHMemory(5),             -- use is Flash Memory
    memoryArrayUseIsNonVolatileRAMMemory(6),    -- use is Nonvolatile RAM
    memoryArrayUseIsCacheMemory(7)              -- use is Cache Memory
}
DellPhysicalMemoryArrayECCType                  ::= INTEGER {
    memoryArrayECCTypeIsOther(1),               -- ECC type is other than following values
    memoryArrayECCTypeIsUnknown(2),             -- ECC type is unknown
    memoryArrayECCTypeIsNone(3),                -- ECC type is none
    memoryArrayECCTypeIsParity(4),              -- ECC type is Parity
    memoryArrayECCTypeIsSingleBitECC(5),        -- ECC type is Single bit ECC
    memoryArrayECCTypeIsMultiBitECC(6),         -- ECC type is Multibit ECC
    memoryArrayECCTypeIsCRC(7)                  -- ECC type is CRC
}

PhysicalMemoryArrayTableEntry                            ::= SEQUENCE {
    physicalMemoryArraychassisIndex                      DellObjectRange,
    physicalMemoryArrayIndex                             DellObjectRange,
    physicalMemoryArrayStateCapabilities                 DellStateCapabilities,
    physicalMemoryArrayStateSettings                     DellStateSettings,
    physicalMemoryArrayStatus                            DellStatus,
    physicalMemoryArrayUse                               DellPhysicalMemoryArrayUse,
    physicalMemoryArrayECCType                           DellPhysicalMemoryArrayECCType,
    physicalMemoryArrayLocation                          DellPhysicalMemoryArrayLocation,
    physicalMemoryArrayMaximumSize                       DellUnsigned32BitRange,
    physicalMemoryArrayTotalNumberSockets                DellUnsigned32BitRange,
    physicalMemoryArrayInUseNumberSockets                DellUnsigned32BitRange,
    physicalMemoryArrayECCErrorNonRecoverableThreshold   DellSigned32BitRange,
    physicalMemoryArrayECCErrorCriticalThreshold         DellSigned32BitRange,
    physicalMemoryArrayECCErrorNonCriticalThreshold      DellSigned32BitRange,
    physicalMemoryArrayRedundantMemoryUnitIndexReference DellObjectRange
}

physicalMemoryArrayTable                        OBJECT-TYPE
    SYNTAX      SEQUENCE OF PhysicalMemoryArrayTableEntry
    ACCESS      not-accessible
    STATUS      mandatory
    DESCRIPTION
"1300.0010 This object defines the Physical Memory Array Table."
    ::= { memoryGroup 10 }
physicalMemoryArrayTableEntry                   OBJECT-TYPE
    SYNTAX      PhysicalMemoryArrayTableEntry
    ACCESS      not-accessible
    STATUS      mandatory
    DESCRIPTION
"1300.0010.0001 This object defines the Physical Memory Array Table Entry."
    INDEX       { physicalMemoryArraychassisIndex,
                  physicalMemoryArrayIndex }
    ::= { physicalMemoryArrayTable 1 }

physicalMemoryArraychassisIndex                 OBJECT-TYPE
    SYNTAX      DellObjectRange
    ACCESS      read-only
    STATUS      mandatory
    DESCRIPTION
"1300.0010.0001.0001 This attribute defines the index (one based) of the
associated chassis."
    ::= { physicalMemoryArrayTableEntry 1 }
physicalMemoryArrayIndex                        OBJECT-TYPE
    SYNTAX      DellObjectRange
    ACCESS      read-only
    STATUS      mandatory
    DESCRIPTION
"1300.0010.0001.0002 This attribute defines the index (one based) of the
physical memory array."
    ::= { physicalMemoryArrayTableEntry 2 }
physicalMemoryArrayStateCapabilities            OBJECT-TYPE
    SYNTAX      DellStateCapabilities
    ACCESS      read-only
    STATUS      mandatory
    DESCRIPTION
"1300.0010.0001.0003 This attribute defines the state capabilities of the
physical memory array."
    ::= { physicalMemoryArrayTableEntry 3 }
physicalMemoryArrayStateSettings                OBJECT-TYPE
    SYNTAX      DellStateSettings
    ACCESS      read-write
    STATUS      mandatory
    DESCRIPTION
"1300.0010.0001.0004 This attribute defines the state settings of the
physical memory array."
    ::= { physicalMemoryArrayTableEntry 4 }
physicalMemoryArrayStatus                       OBJECT-TYPE
    SYNTAX      DellStatus
    ACCESS      read-only
    STATUS      mandatory
    DESCRIPTION
"1300.0010.0001.0005 This attribute defines the status of the physical
memory array."
    ::= { physicalMemoryArrayTableEntry 5 }
physicalMemoryArrayUse                          OBJECT-TYPE
    SYNTAX      DellPhysicalMemoryArrayUse
    ACCESS      read-only
    STATUS      mandatory
    DESCRIPTION
"1300.0010.0001.0006 This attribute defines the use of the physical
memory array."
    ::= { physicalMemoryArrayTableEntry 6 }
physicalMemoryArrayECCType                      OBJECT-TYPE
    SYNTAX      DellPhysicalMemoryArrayECCType
    ACCESS      read-only
    STATUS      mandatory
    DESCRIPTION
"1300.0010.0001.0007 This attribute defines the error correction type used
by the physical memory array."
    ::= { physicalMemoryArrayTableEntry 7 }
physicalMemoryArrayLocation                     OBJECT-TYPE
    SYNTAX      DellPhysicalMemoryArrayLocation
    ACCESS      read-only
    STATUS      mandatory
    DESCRIPTION
"1300.0010.0001.0008 This attribute defines the location of the physical
memory array."
    ::= { physicalMemoryArrayTableEntry 8 }
physicalMemoryArrayMaximumSize                  OBJECT-TYPE
    SYNTAX      DellUnsigned32BitRange
    ACCESS      read-only
    STATUS      mandatory
    DESCRIPTION
"1300.0010.0001.0009 This attribute defines the maximum size in KBytes
of the physical memory array.  Zero inicates no memory is installed.
2,147,483,647 indicates an unknown maximum size."
    ::= { physicalMemoryArrayTableEntry 9 }
physicalMemoryArrayTotalNumberSockets           OBJECT-TYPE
    SYNTAX      DellUnsigned32BitRange
    ACCESS      read-only
    STATUS      mandatory
    DESCRIPTION
"1300.0010.0001.0010 This attribute defines the total number of memory
sockets available for the physical memory array.  2,147,483,647 indicates
an unknown number of sockets."
    ::= { physicalMemoryArrayTableEntry 10 }
physicalMemoryArrayInUseNumberSockets           OBJECT-TYPE
    SYNTAX      DellUnsigned32BitRange
    ACCESS      read-only
    STATUS      mandatory
    DESCRIPTION
"1300.0010.0001.0011 This attribute defines the total number of memory
sockets in use by the physical memory array.  2,147,483,647 indicates
an unknown number of sockets."
    ::= { physicalMemoryArrayTableEntry 11 }
physicalMemoryArrayECCErrorNonRecoverableThreshold OBJECT-TYPE
    SYNTAX      DellSigned32BitRange
    ACCESS      read-only
    STATUS      mandatory
    DESCRIPTION
"1300.0010.0001.0012 This attribute defines the value of the physical
memory array ECC error nonrecoverable threshold.  The value is an integer
representing the number of errors detected."
    ::= { physicalMemoryArrayTableEntry 12 }
physicalMemoryArrayECCErrorCriticalThreshold    OBJECT-TYPE
    SYNTAX      DellSigned32BitRange
    ACCESS      read-only
    STATUS      mandatory
    DESCRIPTION
"1300.0010.0001.00013 This attribute defines the value of the physical
memory array ECC error critical threshold.  The value is an integer
representing the number of errors detected."
    ::= { physicalMemoryArrayTableEntry 13 }
physicalMemoryArrayECCErrorNonCriticalThreshold OBJECT-TYPE
    SYNTAX      DellSigned32BitRange
    ACCESS      read-write
    STATUS      mandatory
    DESCRIPTION
"1300.0010.0001.00014 This attribute defines the value of the physical
memory array ECC error noncritical threshold.  The value is an integer
representing the number of errors detected."
    ::= { physicalMemoryArrayTableEntry 14 }
physicalMemoryArrayRedundantMemoryUnitIndexReference OBJECT-TYPE
    SYNTAX      DellObjectRange
    ACCESS      read-only
    STATUS      mandatory
    DESCRIPTION
"1300.0010.0001.0015 This attribute defines the index to the associated
redundant memory unit if this physical memory array is part of a redundant
memory unit."
    ::= { physicalMemoryArrayTableEntry 15 }


-------------------------------------------------------------------------------
-- Physical Memory Array Mapped Table
--
-- OID Format: 1.3.6.1.4.1.674.10892.1.1300.20.1.<a>.<i1>.<i2>
-------------------------------------------------------------------------------

PhysicalMemoryArrayMappedTableEntry             ::= SEQUENCE {
    physicalMemoryArrayMappedchassisIndex       DellObjectRange,
    physicalMemoryArrayMappedIndex              DellObjectRange,
    physicalMemoryArrayMappedStateCapabilities  DellStateCapabilities,
    physicalMemoryArrayMappedStateSettings      DellStateSettings,
    physicalMemoryArrayMappedStatus             DellStatus,
    physicalMemoryArrayIndexReference           DellObjectRange,
    physicalMemoryArrayMappedStartingAddress    DellUnsigned64BitRange,
    physicalMemoryArrayMappedEndingAddress      DellUnsigned64BitRange,
    physicalMemoryArrayMappedPartitionWidth     DellUnsigned32BitRange
}

physicalMemoryArrayMappedTable                  OBJECT-TYPE
    SYNTAX      SEQUENCE OF PhysicalMemoryArrayMappedTableEntry
    ACCESS      not-accessible
    STATUS      mandatory
    DESCRIPTION
"1300.0020 This object defines the Physical Memory Array Mapped Table."
    ::= { memoryGroup 20 }
physicalMemoryArrayMappedTableEntry             OBJECT-TYPE
    SYNTAX      PhysicalMemoryArrayMappedTableEntry
    ACCESS      not-accessible
    STATUS      mandatory
    DESCRIPTION
"1300.0020.0001 This object defines the Physical Memory Array Mapped
Table Entry."
    INDEX       { physicalMemoryArrayMappedchassisIndex,
                  physicalMemoryArrayMappedIndex }
    ::= { physicalMemoryArrayMappedTable 1 }

physicalMemoryArrayMappedchassisIndex           OBJECT-TYPE
    SYNTAX      DellObjectRange
    ACCESS      read-only
    STATUS      mandatory
    DESCRIPTION
"1300.0020.0001.0001 This attribute defines the index (one based) of the
associated chassis."
    ::= { physicalMemoryArrayMappedTableEntry 1 }
physicalMemoryArrayMappedIndex                  OBJECT-TYPE
    SYNTAX      DellObjectRange
    ACCESS      read-only
    STATUS      mandatory
    DESCRIPTION
"1300.0020.0001.0002 This attribute defines the index (one based) of the
physical memory array mapped address."
    ::= { physicalMemoryArrayMappedTableEntry 2 }
physicalMemoryArrayMappedStateCapabilities      OBJECT-TYPE
    SYNTAX      DellStateCapabilities
    ACCESS      read-only
    STATUS      mandatory
    DESCRIPTION
"1300.0020.0001.0003 This attribute defines the state capabilities of the
physical memory array mapped address."
    ::= { physicalMemoryArrayMappedTableEntry 3 }
physicalMemoryArrayMappedStateSettings          OBJECT-TYPE
    SYNTAX      DellStateSettings
    ACCESS      read-write
    STATUS      mandatory
    DESCRIPTION
"1300.0020.0001.0004 This attribute defines the state settings of the
physical memory array mapped address."
    ::= { physicalMemoryArrayMappedTableEntry 4 }
physicalMemoryArrayMappedStatus                 OBJECT-TYPE
    SYNTAX      DellStatus
    ACCESS      read-only
    STATUS      mandatory
    DESCRIPTION
"1300.0020.0001.0005 This attribute defines the status of the
physical memory array mapped address."
    ::= { physicalMemoryArrayMappedTableEntry 5 }
physicalMemoryArrayIndexReference               OBJECT-TYPE
    SYNTAX      DellObjectRange
    ACCESS      read-only
    STATUS      mandatory
    DESCRIPTION
"1300.0020.0001.0006 This attribute defines the index (one based) of the
associated physical memory array."
    ::= { physicalMemoryArrayMappedTableEntry 6 }
physicalMemoryArrayMappedStartingAddress        OBJECT-TYPE
    SYNTAX      DellUnsigned64BitRange
    ACCESS      read-only
    STATUS      mandatory
    DESCRIPTION
"1300.0020.0001.0007 This attribute defines the physical starting address
in KBytes of the physical memory array mapped address."
    ::= { physicalMemoryArrayMappedTableEntry 7 }
physicalMemoryArrayMappedEndingAddress          OBJECT-TYPE
    SYNTAX      DellUnsigned64BitRange
    ACCESS      read-only
    STATUS      mandatory
    DESCRIPTION
"1300.0020.0001.0008 This attribute defines the physical ending address
in KBytes of the physical memory array mapped address."
    ::= { physicalMemoryArrayMappedTableEntry 8 }
physicalMemoryArrayMappedPartitionWidth         OBJECT-TYPE
    SYNTAX      DellUnsigned32BitRange
    ACCESS      read-only
    STATUS      mandatory
    DESCRIPTION
"1300.0020.0001.0009 This attribute defines the number of memory devices
that form a single row in the memory array mapped address.  2,147,483,647
indicates an unknown number of memory devices."
    ::= { physicalMemoryArrayMappedTableEntry 9 }


-------------------------------------------------------------------------------
-- Physical Memory Configuration Table
--
-- OID Format: 1.3.6.1.4.1.674.10892.1.1300.30.1.<a>.<i1>.<i2>
-------------------------------------------------------------------------------

DellPhysicalMemoryConfigStateCapabilities       ::= INTEGER {
    -- none(0),                                 -  no state capabilities supported
    unknownCapabilities(1),                     -- state capabilities are unknown
    enableCapable(2),                           -- memory config can be enabled and disabled
    notReadyCapable(4)                          -- memory config can be not ready
}
DellPhysicalMemoryConfigStateSettings           ::= INTEGER {
    -- none(0),                                 -  no state settings enabled
    unknown(1),                                 -- state settings are unknown
    enabled(2),                                 -- memory config is enabled
    notReady(4),                                -- memory config is not ready
    redundantMemoryIsActive(8),                 -- redundant memory is active (in use)
    enabledAndRedundantMemoryIsActive(10)
}
DellPhysicalMemoryConfigRedundantCapabilities   ::= INTEGER {
    -- none(0),                                 -  no redundant capabilities supported
    unknownCapabilities(1),                     -- redundant capabilities are unknown
    spareCapable(2),                            -- Spare redundancy is supported
    mirrorCapable(4),                           -- Mirror redundancy is supported
    spareAndMirrorCapable(6),
    raidCapable(8),                             -- RAID redundancy is supported
    dddcCapable(16)                             -- DDDC redundancy is supported
}
DellPhysicalMemoryConfigRedundantSettings       ::= INTEGER {
    -- none(0),                                 -  no redundant settings enabled
    unknown(1),                                 -- redundant settings are unknown
    -- The following settings are mutually exclusive:
    spareEnabled(2),                            -- Spare redundancy is enabled
    mirrorEnabled(4),                           -- Mirror redundancy is enabled
    raidEnabled(8),                             -- RAID redundancy is enabled
    dddcEnabled(16)                             -- DDDC redundancy is enabled
}
DellPhysicalMemoryConfigMOMCapabilities         ::= INTEGER {
    -- none(0),                                 -  no memory operating mode capabilities supported
    unknownCapabilities(1),                     -- memory operating mode capabilities are unknown
    momOptimizerCapable(2),                     -- Optimizer mode is supported
    momSpareCapable(4),                         -- Spare mode is supported
    momMirrorCapable(8),                        -- Mirror mode is supported
    momAdvancedECCCapable(16)                   -- Advanced ECC mode is supported
}
DellPhysicalMemoryConfigMOMSettings             ::= INTEGER {
    -- none(0),                                 -  no memory operating mode settings enabled
    unknown(1),                                 -- memory operating mode settings are unknown
    -- The following settings are mutually exclusive:
    momOptimizerEnabled(2),                     -- Optimizer mode is enabled
    momSpareEnabled(4),                         -- Spare mode is enabled
    momMirrorEnabled(8),                        -- Mirror mode is enabled
    momAdvancedECCEnabled(16)                   -- Advanced ECC mode is enabled
}

PhysicalMemoryConfigTableEntry                  ::= SEQUENCE {
    physicalMemoryConfigChassisIndex            DellObjectRange,
    physicalMemoryConfigIndex                   DellObjectRange,
    physicalMemoryConfigStateCapabilities       DellPhysicalMemoryConfigStateCapabilities,
    physicalMemoryConfigStateSettings           DellPhysicalMemoryConfigStateSettings,
    physicalMemoryConfigStatus                  DellStatus,
    physicalMemoryConfigRedundantCapabilities   DellPhysicalMemoryConfigRedundantCapabilities,
    physicalMemoryConfigRedundantSettings       DellPhysicalMemoryConfigRedundantSettings,
    physicalMemoryConfigMOMCapabilities         DellPhysicalMemoryConfigMOMCapabilities,
    physicalMemoryConfigMOMSettings             DellPhysicalMemoryConfigMOMSettings
}

physicalMemoryConfigTable                       OBJECT-TYPE
    SYNTAX      SEQUENCE OF PhysicalMemoryConfigTableEntry
    ACCESS      not-accessible
    STATUS      mandatory
    DESCRIPTION
"1300.0030 This object defines the Physical Memory Configuration Table."
    ::= { memoryGroup 30 }
physicalMemoryConfigTableEntry                  OBJECT-TYPE
    SYNTAX      PhysicalMemoryConfigTableEntry
    ACCESS      not-accessible
    STATUS      mandatory
    DESCRIPTION
"1300.0030.0001 This object defines the Physical Memory Configuration
Table Entry."
    INDEX       { physicalMemoryConfigChassisIndex,
                  physicalMemoryConfigIndex }
    ::= { physicalMemoryConfigTable 1 }

physicalMemoryConfigChassisIndex                OBJECT-TYPE
    SYNTAX      DellObjectRange
    ACCESS      read-only
    STATUS      mandatory
    DESCRIPTION
"1300.0030.0001.0001 This attribute defines the index (one based) of the
associated chassis."
    ::= { physicalMemoryConfigTableEntry 1 }
physicalMemoryConfigIndex                       OBJECT-TYPE
    SYNTAX      DellObjectRange
    ACCESS      read-only
    STATUS      mandatory
    DESCRIPTION
"1300.0030.0001.0002 This attribute defines the index (one based) of the
physical memory configuration."
    ::= { physicalMemoryConfigTableEntry 2 }
physicalMemoryConfigStateCapabilities           OBJECT-TYPE
    SYNTAX      DellPhysicalMemoryConfigStateCapabilities
    ACCESS      read-only
    STATUS      mandatory
    DESCRIPTION
"1300.0030.0001.0003 This attribute defines the state capabilities of the
physical memory configuration."
    ::= { physicalMemoryConfigTableEntry 3 }
physicalMemoryConfigStateSettings               OBJECT-TYPE
    SYNTAX      DellPhysicalMemoryConfigStateSettings
    ACCESS      read-write
    STATUS      mandatory
    DESCRIPTION
"1300.0030.0001.0004 This attribute defines the state settings of the
physical memory configuration."
    ::= { physicalMemoryConfigTableEntry 4 }
physicalMemoryConfigStatus                      OBJECT-TYPE
    SYNTAX      DellStatus
    ACCESS      read-only
    STATUS      mandatory
    DESCRIPTION
"1300.0030.0001.0005 This attribute defines the status of the
physical memory configuration."
    ::= { physicalMemoryConfigTableEntry 5 }
physicalMemoryConfigRedundantCapabilities       OBJECT-TYPE
    SYNTAX      DellPhysicalMemoryConfigRedundantCapabilities
    ACCESS      read-only
    STATUS      mandatory
    DESCRIPTION
"1300.0030.0001.0006 This attribute defines the redundant capabilities of the
physical memory."
    ::= { physicalMemoryConfigTableEntry 6 }
physicalMemoryConfigRedundantSettings           OBJECT-TYPE
    SYNTAX      DellPhysicalMemoryConfigRedundantSettings
    ACCESS      read-write
    STATUS      mandatory
    DESCRIPTION
"1300.0030.0001.0007 This attribute defines the redundant settings of the
physical memory."
    ::= { physicalMemoryConfigTableEntry 7 }
physicalMemoryConfigMOMCapabilities             OBJECT-TYPE
    SYNTAX      DellPhysicalMemoryConfigMOMCapabilities
    ACCESS      read-only
    STATUS      mandatory
    DESCRIPTION
"1300.0030.0001.0008 This attribute defines the Memory Operating Mode capabilities
of the physical memory."
    ::= { physicalMemoryConfigTableEntry 8 }
physicalMemoryConfigMOMSettings                 OBJECT-TYPE
    SYNTAX      DellPhysicalMemoryConfigMOMSettings
    ACCESS      read-only
    STATUS      mandatory
    DESCRIPTION
"1300.0030.0001.0009 This attribute defines the Memory Operating Mode settings
of the physical memory."
    ::= { physicalMemoryConfigTableEntry 9 }


-------------------------------------------------------------------------------
-- Physical Memory Logging Table
--
-- OID Format: 1.3.6.1.4.1.674.10892.1.1300.40.1.<a>.<i1>.<i2>
-------------------------------------------------------------------------------

DellPhysicalMemoryLoggingCapabilities           ::= INTEGER {
    -- If set to 0 (zero), there are no Logging capabilities
    unknownCapabilities(1),                     -- logging capabilities are unknown
    enableCapable(2)                            -- logging can be enabled or disabled
}
DellPhysicalMemoryLoggingSettings               ::= INTEGER {
    -- If set to 0 (zero), there are no Logging settings enabled
    unknown(1),                                 -- logging settings are unknown
    enabled(2)                                  -- logging is enabled
}

PhysicalMemoryLoggingTableEntry                 ::= SEQUENCE {
    physicalMemoryLoggingChassisIndex           DellObjectRange,
    physicalMemoryLoggingIndex                  DellObjectRange,
    physicalMemoryLoggingCapabilities           DellPhysicalMemoryLoggingCapabilities,
    physicalMemoryLoggingSettings               DellPhysicalMemoryLoggingSettings,
    physicalMemoryLoggingStatus                 DellStatus
}

physicalMemoryLoggingTable                      OBJECT-TYPE
    SYNTAX      SEQUENCE OF PhysicalMemoryLoggingTableEntry
    ACCESS      not-accessible
    STATUS      mandatory
    DESCRIPTION
"1300.0040 This object defines the Physical Memory Logging Table."
    ::= { memoryGroup 40 }
physicalMemoryLoggingTableEntry                 OBJECT-TYPE
    SYNTAX      PhysicalMemoryLoggingTableEntry
    ACCESS      not-accessible
    STATUS      mandatory
    DESCRIPTION
"1300.0040.0001 This object defines the Physical Memory Logging Table Entry."
    INDEX       { physicalMemoryLoggingChassisIndex,
                  physicalMemoryLoggingIndex }
    ::= { physicalMemoryLoggingTable 1 }

physicalMemoryLoggingChassisIndex               OBJECT-TYPE
    SYNTAX      DellObjectRange
    ACCESS      read-only
    STATUS      mandatory
    DESCRIPTION
"1300.0040.0001.0001 This attribute defines the index (one based) of the
associated chassis."
    ::= { physicalMemoryLoggingTableEntry 1 }
physicalMemoryLoggingIndex                      OBJECT-TYPE
    SYNTAX      DellObjectRange
    ACCESS      read-only
    STATUS      mandatory
    DESCRIPTION
"1300.0040.0001.0002 This attribute defines the index (one based) of the
physical memory logging."
    ::= { physicalMemoryLoggingTableEntry 2 }
physicalMemoryLoggingCapabilities               OBJECT-TYPE
    SYNTAX      DellPhysicalMemoryLoggingCapabilities
    ACCESS      read-only
    STATUS      mandatory
    DESCRIPTION
"1300.0040.0001.0003 This attribute defines the capabilities of the
physical memory logging."
    ::= { physicalMemoryLoggingTableEntry 3 }
physicalMemoryLoggingSettings                   OBJECT-TYPE
    SYNTAX      DellPhysicalMemoryLoggingSettings
    ACCESS      read-write
    STATUS      mandatory
    DESCRIPTION
"1300.0040.0001.0004 This attribute defines the settings of the
physical memory logging."
    ::= { physicalMemoryLoggingTableEntry 4 }
physicalMemoryLoggingStatus                     OBJECT-TYPE
    SYNTAX      DellStatus
    ACCESS      read-only
    STATUS      mandatory
    DESCRIPTION
"1300.0040.0001.0005 This attribute defines the status of the
physical memory logging."
    ::= { physicalMemoryLoggingTableEntry 5 }


-------------------------------------------------------------------------------
-- Redundant Memory Unit Table
--
-- OID Format: 1.3.6.1.4.1.674.10892.1.1300.50.1.<a>.<i1>.<i2>
-------------------------------------------------------------------------------

RedundantMemoryUnitTableEntry                   ::= SEQUENCE {
    redundantMemoryUnitChassisIndex             DellObjectRange,
    redundantMemoryUnitIndex                    DellObjectRange,
    redundantMemoryUnitStateCapabilities        DellStateCapabilities,
    redundantMemoryUnitStateSettings            DellStateSettings,
    redundantMemoryUnitRedundancyStatus         DellStatusRedundancy,
    redundantMemoryUnitName                     DellString,
    redundantMemoryUnitStatus                   DellStatus
}

redundantMemoryUnitTable                        OBJECT-TYPE
    SYNTAX      SEQUENCE OF RedundantMemoryUnitTableEntry
    ACCESS      not-accessible
    STATUS      mandatory
    DESCRIPTION
"1300.0050 This object defines the Redundant Memory Unit Table."
    ::= { memoryGroup 50 }
redundantMemoryUnitTableEntry                   OBJECT-TYPE
    SYNTAX      RedundantMemoryUnitTableEntry
    ACCESS      not-accessible
    STATUS      mandatory
    DESCRIPTION
"1300.0050.0001 This object defines the Redundant Memory Unit Table Entry."
    INDEX       { redundantMemoryUnitChassisIndex,
                  redundantMemoryUnitIndex }
    ::= { redundantMemoryUnitTable 1 }

redundantMemoryUnitChassisIndex                 OBJECT-TYPE
    SYNTAX      DellObjectRange
    ACCESS      read-only
    STATUS      mandatory
    DESCRIPTION
"1300.0050.0001.0001 This attribute defines the index (one based) of the
associated chassis."
    ::= { redundantMemoryUnitTableEntry 1 }
redundantMemoryUnitIndex                        OBJECT-TYPE
    SYNTAX      DellObjectRange
    ACCESS      read-only
    STATUS      mandatory
    DESCRIPTION
"1300.0050.0001.0002 This attribute defines the index (one based) of the
redundant memory unit."
    ::= { redundantMemoryUnitTableEntry 2 }
redundantMemoryUnitStateCapabilities            OBJECT-TYPE
    SYNTAX      DellStateCapabilities
    ACCESS      read-only
    STATUS      mandatory
    DESCRIPTION
"1300.0050.0001.0003 This attribute defines the state capabilities of the
redundant memory unit."
    ::= { redundantMemoryUnitTableEntry 3 }
redundantMemoryUnitStateSettings                OBJECT-TYPE
    SYNTAX      DellStateSettings
    ACCESS      read-write
    STATUS      mandatory
    DESCRIPTION
"1300.0050.0001.0004 This attribute defines the state settings of the
redundant memory unit."
    ::= { redundantMemoryUnitTableEntry 4 }
redundantMemoryUnitRedundancyStatus             OBJECT-TYPE
    SYNTAX      DellStatusRedundancy
    ACCESS      read-only
    STATUS      mandatory
    DESCRIPTION
"1300.0050.0001.0005 This attribute defines the redundancy status of the
redundant memory unit."
    ::= { redundantMemoryUnitTableEntry 5 }
redundantMemoryUnitName                         OBJECT-TYPE
    SYNTAX      DellString
    ACCESS      read-only
    STATUS      mandatory
    DESCRIPTION
"1300.0050.0001.0006 This attribute defines the name of the
redundant memory unit."
    ::= { redundantMemoryUnitTableEntry 6 }
redundantMemoryUnitStatus                       OBJECT-TYPE
    SYNTAX      DellStatus
    ACCESS      read-only
    STATUS      mandatory
    DESCRIPTION
"1300.0050.0001.0007 This attribute defines the status of the
redundant memory unit."
    ::= { redundantMemoryUnitTableEntry 7 }


-------------------------------------------------------------------------------
-- Physical Memory Card Table
--
-- OID Format: 1.3.6.1.4.1.674.10892.1.1300.60.1.<a>.<i1>.<i2>
-------------------------------------------------------------------------------

PhysicalMemoryCardTableEntry                    ::= SEQUENCE {
    physicalMemoryCardChassisIndex              DellObjectRange,
    physicalMemoryCardIndex                     DellObjectRange,
    physicalMemoryCardStateCapabilities         DellStateCapabilities,
    physicalMemoryCardStateSettings             DellStateSettings,
    physicalMemoryCardStatus                    DellStatus,
    physicalMemoryCardName                      DellString,
    physicalMemoryCardTotalNumberSockets        DellUnsigned32BitRange,
    physicalMemoryCardInUseNumberSockets        DellUnsigned32BitRange,
    physicalMemoryCardPhyMemArrayIndexReference DellObjectRange
}

physicalMemoryCardTable                         OBJECT-TYPE
    SYNTAX      SEQUENCE OF PhysicalMemoryCardTableEntry
    ACCESS      not-accessible
    STATUS      mandatory
    DESCRIPTION
"1300.0060 This object defines the Physical Memory Card Table."
    ::= { memoryGroup 60 }
physicalMemoryCardTableEntry                    OBJECT-TYPE
    SYNTAX      PhysicalMemoryCardTableEntry
    ACCESS      not-accessible
    STATUS      mandatory
    DESCRIPTION
"1300.0060.0001 This object defines the Physical Memory Card Table Entry."
    INDEX       { physicalMemoryCardChassisIndex,
                  physicalMemoryCardIndex }
    ::= { physicalMemoryCardTable 1 }

physicalMemoryCardChassisIndex                  OBJECT-TYPE
    SYNTAX      DellObjectRange
    ACCESS      read-only
    STATUS      mandatory
    DESCRIPTION
"1300.0060.0001.0001 This attribute defines the index (one based) of the
associated chassis."
    ::= { physicalMemoryCardTableEntry 1 }
physicalMemoryCardIndex                         OBJECT-TYPE
    SYNTAX      DellObjectRange
    ACCESS      read-only
    STATUS      mandatory
    DESCRIPTION
"1300.0060.0001.0002 This attribute defines the index (one based) of the
physical memory card."
    ::= { physicalMemoryCardTableEntry 2 }
physicalMemoryCardStateCapabilities             OBJECT-TYPE
    SYNTAX      DellStateCapabilities
    ACCESS      read-only
    STATUS      mandatory
    DESCRIPTION
"1300.0060.0001.0003 This attribute defines the state capabilities of the
physical memory card."
    ::= { physicalMemoryCardTableEntry 3 }
physicalMemoryCardStateSettings                 OBJECT-TYPE
    SYNTAX      DellStateSettings
    ACCESS      read-write
    STATUS      mandatory
    DESCRIPTION
"1300.0060.0001.0004 This attribute defines the state settings of the
physical memory card."
    ::= { physicalMemoryCardTableEntry 4 }
physicalMemoryCardStatus                        OBJECT-TYPE
    SYNTAX      DellStatus
    ACCESS      read-only
    STATUS      mandatory
    DESCRIPTION
"1300.0060.0001.0005 This attribute defines the status of the
physical memory card."
    ::= { physicalMemoryCardTableEntry 5 }
physicalMemoryCardName                          OBJECT-TYPE
    SYNTAX      DellString
    ACCESS      read-only
    STATUS      mandatory
    DESCRIPTION
"1300.0060.0001.0006 This attribute defines the name of the
physical memory card."
    ::= { physicalMemoryCardTableEntry 6 }
physicalMemoryCardTotalNumberSockets            OBJECT-TYPE
    SYNTAX      DellUnsigned32BitRange
    ACCESS      read-only
    STATUS      mandatory
    DESCRIPTION
"1300.0060.0001.0007 This attribute defines the total number of memory
sockets available on the physical memory card.  2,147,483,647 indicates
an unknown number of sockets."
    ::= { physicalMemoryCardTableEntry 7 }
physicalMemoryCardInUseNumberSockets            OBJECT-TYPE
    SYNTAX      DellUnsigned32BitRange
    ACCESS      read-only
    STATUS      mandatory
    DESCRIPTION
"1300.0060.0001.0008 This attribute defines the number of memory
sockets in use on the physical memory card.  Zero indicates that the
physical memory card is not installed or has a configuration error.
2,147,483,647 indicates an unknown number of sockets."
    ::= { physicalMemoryCardTableEntry 8 }
physicalMemoryCardPhyMemArrayIndexReference     OBJECT-TYPE
    SYNTAX      DellObjectRange
    ACCESS      read-only
    STATUS      mandatory
    DESCRIPTION
"1300.0060.0001.0009 This attribute defines the index (one based) of the
Physical Memory Array Table entry for the physical memory array with the
same chassis index that this physical memory card is associated with."
    ::= { physicalMemoryCardTableEntry 9 }


-------------------------------------------------------------------------------
-- BIOS Setup Control Group
--
-- OID Format: 1.3.6.1.4.1.674.10892.1.1400
-------------------------------------------------------------------------------


-------------------------------------------------------------------------------
-- BIOS Setup Control Table
--
-- OID Format: 1.3.6.1.4.1.674.10892.1.1400.10.1.<a>.<i1>
-------------------------------------------------------------------------------

DellSpeakerControlCapabilitiesUnique            ::= INTEGER {
    unknown(1),                                 -- speaker control capabilities are unknown
    enableCapable(2),                           -- speaker can be enabled or disabled
    lowCapable(4),                              -- speaker volume can be set to low
    mediumCapable(8),                           -- speaker volume can be set to medium
    highCapable(16),                            -- speaker volume can be set to high
    allVolumeCapable(30)                        -- speaker volume can be set to low, medium or high
}
DellSpeakerControlSettingsUnique                ::= INTEGER {
    unknown(1),                                 -- speaker control settings are unknown
    enabled(2),                                 -- speaker is enabled
    low(4),                                     -- speaker volume is low
    medium(8),                                  -- speaker volume is medium
    high(16)                                    -- speaker volume is high
}
DellNIFwakeonLanControlCapabilitiesUnique       ::= INTEGER {
    unknown(1),                                 -- wake on LAN capabilities are unknown
    enableCapable(2),                           -- wake on LAN can be enabled or disabled
    addInCardCapable(4),                        -- wake on LAN by add in card capable
    onBoardCapable(8),                          -- wake on LAN by onboard NIF capable
    bothCapable(14)
}
DellNIFwakeonLanControlSettingsUnique           ::= INTEGER {
    unknown(1),                                 -- wake on LAN settings are unknown
    enabled(2),                                 -- wake on LAN is enabled
    addInCard(4),                               -- wake on LAN is by add in card
    onBoard(8),                                 -- wake on LAN is by onboard NIF
    addInCardOrOnBoard(12)                      -- wake on LAN is by either add in card or onboard NIF
}
DellBootSequenceControlCapabilitiesUnique       ::= INTEGER {
    bootSequenceUnknown(1),                     -- boot sequence capabilities are unknown
    bootFromDisketteFirstCapable(2),            -- boot sequence can be diskette first
    bootFromHardDriveFirstCapable(4),           -- boot sequence can be IDE hard drive first
    bootFromDisketteORHardDriveFirstCapable(6), -- boot sequence can be diskette or IDE hard drive first
    bootFromDeviceListCapable(8),               -- boot sequence can be device list
    bootFromCDROMFirstCapable(16),              -- boot sequence can be CD ROM first
    allFirstCapable(30)                         -- boot sequence can be any of the above methods first
}
DellBootSequenceControlSettingsUnique           ::= INTEGER {
    bootSequenceUnknown(1),                     -- boot sequence settings are unknown
    bootFromDisketteFirst(2),                   -- boot sequence is diskette first
    bootFromHardDriveFirst(4),                  -- boot sequence is IDE hard drive first
    bootFromDeviceList(8),                      -- boot sequence is device list
    bootFromCDROMFirst(16)                      -- boot sequence is CD ROM first
}
DellBIOSPasswordControlCapabilitiesUnique       ::= INTEGER {
    passwordControlCapabilitiesUnknown(1),      -- BIOS password capabilities are unknown
    passwordControlEnableCapable(2),            -- BIOS password can be enabled
    passwordControlJumperDisableCapable(4),     -- BIOS password can be jumper disabled
    passwordControlEnableAndJumperDisableCapable(6)
}
DellBIOSPasswordControlSettingsUnique           ::= INTEGER {
    passwordControlSettingsUnknown(1),          -- BIOS password settings are unknown
    passwordControlEnabled(2),                  -- BIOS password is enabled
    passwordControlJumperDisabled(4)            -- BIOS password has been disabled by jumper
}
DellTPMSecurityControlCapabilities              ::= INTEGER {
    -- Note: These values are bit masks, so combination values are possible.
    offCapable(1),                              -- TPM security can be Off
    onWithPrebootMeasurementsCapable(2),        -- TPM security can be On with Pre-boot Measurements
    onWithoutPrebootMeasurementsCapable(4)      -- TPM security can be On without Pre-boot Measurements
}
DellTPMSecurityControlSetting                   ::= INTEGER {
    -- off(0),                                  -  TPM security is Off
    onWithPrebootMeasurements(1),               -- TPM security is On with Pre-boot Measurements
    onWithoutPrebootMeasurements(2)             -- TPM security is On without Pre-boot Measurements
}

BiosSetUpControlTableEntry                              ::= SEQUENCE {
    biosSetUpControlchassisIndex                        DellObjectRange,
    bSUCpointingDeviceControlCapabilities               DellStateCapabilities,
    bSUCpointingDeviceControlSettings                   DellStateSettings,
    bSUCpointingDeviceControlStatus                     DellStatus,
    bSUCpointingDeviceControlName                       DellString,
    bSUCnumLockControlCapabilities                      DellStateCapabilities,
    bSUCnumLockControlSettings                          DellStateSettings,
    bSUCnumLockControlStatus                            DellStatus,
    bSUCnumLockControlName                              DellString,
    bSUCprocessorSerialNumberControlCapabilities        DellStateCapabilities,
    bSUCprocessorSerialNumberControlSettings            DellStateSettings,
    bSUCprocessorSerialNumberControlStatus              DellStatus,
    bSUCprocessorSerialNumberControlName                DellString,
    bSUCspeakerControlCapabilitiesUnique                DellSpeakerControlCapabilitiesUnique,
    bSUCspeakerControlSettingsUnique                    DellSpeakerControlSettingsUnique,
    bSUCspeakerControlStatus                            DellStatus,
    bSUCspeakerControlName                              DellString,
    bSUCnIFwakeonLanControlCapabilitiesUnique           DellNIFwakeonLanControlCapabilitiesUnique,
    bSUCnIFwakeonLanControlSettingsUnique               DellNIFwakeonLanControlSettingsUnique,
    bSUCnIFwakeonLanControlStatus                       DellStatus,
    bSUCnIFwakeonLanControlName                         DellString,
    bSUCbootSequenceControlCapabilitiesUnique           DellBootSequenceControlCapabilitiesUnique,
    bSUCbootSequenceControlSettingsUnique               DellBootSequenceControlSettingsUnique,
    bSUCbootSequenceControlStatus                       DellStatus,
    bSUCbootSequenceControlName                         DellString,
    bSUCadministratorPasswordControlCapabilitiesUnique  DellBIOSPasswordControlCapabilitiesUnique,
    bSUCadministratorPasswordControlSettingsUnique      DellBIOSPasswordControlSettingsUnique,
    bSUCadministratorPasswordControlStatus              DellStatus,
    bSUCadministratorPasswordPasswordVerifyName         DellString,
    bSUCadministratorPasswordNewPasswordName            DellString,
    bSUCuserPasswordControlCapabilitiesUnique           DellBIOSPasswordControlCapabilitiesUnique,
    bSUCuserPasswordControlSettingsUnique               DellBIOSPasswordControlSettingsUnique,
    bSUCuserPasswordControlStatus                       DellStatus,
    bSUCuserPasswordPasswordVerifyName                  DellString,
    bSUCuserPasswordNewPasswordName                     DellString,
    bSUCtpmSecurityControlCapabilities                  DellTPMSecurityControlCapabilities,
    bSUCtpmSecurityControlSetting                       DellTPMSecurityControlSetting,
    bSUCtpmSecurityControlStatus                        DellStatus,
    bSUCtpmSecurityControlName                          DellString
}

biosSetUpControlTable                           OBJECT-TYPE
    SYNTAX      SEQUENCE OF BiosSetUpControlTableEntry
    ACCESS      not-accessible
    STATUS      mandatory
    DESCRIPTION
"1400.0010 This object defines the BIOS Setup Control Table."
    ::= { biosSetUpControlGroup 10 }
biosSetUpControlTableEntry                      OBJECT-TYPE
    SYNTAX      BiosSetUpControlTableEntry
    ACCESS      not-accessible
    STATUS      mandatory
    DESCRIPTION
"1400.0010.0001 This object defines the BIOS Setup Control Table Entry."
    INDEX       { biosSetUpControlchassisIndex }
    ::= { biosSetUpControlTable 1 }

biosSetUpControlchassisIndex                    OBJECT-TYPE
    SYNTAX      DellObjectRange
    ACCESS      read-only
    STATUS      mandatory
    DESCRIPTION
"1400.0010.0001.0001 This attribute defines the index (one based) of the
associated chassis."
    ::= { biosSetUpControlTableEntry 1 }
bSUCpointingDeviceControlCapabilities           OBJECT-TYPE
    SYNTAX      DellStateCapabilities
    ACCESS      read-only
    STATUS      mandatory
    DESCRIPTION
"1400.0010.0001.0002 This attribute defines the BIOS setup control capabilities
of the pointing Device."
    ::= { biosSetUpControlTableEntry 2 }
bSUCpointingDeviceControlSettings               OBJECT-TYPE
    SYNTAX      DellStateSettings
    ACCESS      read-write
    STATUS      mandatory
    DESCRIPTION
"1400.0010.0001.0003 This attribute defines the BIOS setup control settings
of the pointing device."
    ::= { biosSetUpControlTableEntry 3 }
bSUCpointingDeviceControlStatus                 OBJECT-TYPE
    SYNTAX      DellStatus
    ACCESS      read-only
    STATUS      mandatory
    DESCRIPTION
"1400.0010.0001.0004 This attribute defines the BIOS setup control status
of the pointing device."
    ::= { biosSetUpControlTableEntry 4 }
bSUCpointingDeviceControlName                   OBJECT-TYPE
    SYNTAX      DellString
    ACCESS      read-only
    STATUS      mandatory
    DESCRIPTION
"1400.0010.0001.0005 This attribute defines the BIOS setup control name
of the pointing device."
    ::= { biosSetUpControlTableEntry 5 }
bSUCnumLockControlCapabilities                  OBJECT-TYPE
    SYNTAX      DellStateCapabilities
    ACCESS      read-only
    STATUS      mandatory
    DESCRIPTION
"1400.0010.0001.0006 This attribute defines the BIOS setup control capabilities
of the numeric lock."
    ::= { biosSetUpControlTableEntry 6 }
bSUCnumLockControlSettings                      OBJECT-TYPE
    SYNTAX      DellStateSettings
    ACCESS      read-write
    STATUS      mandatory
    DESCRIPTION
"1400.0010.0001.0007 This attribute defines the BIOS setup control settings
of the numeric lock."
    ::= { biosSetUpControlTableEntry 7 }
bSUCnumLockControlStatus                        OBJECT-TYPE
    SYNTAX      DellStatus
    ACCESS      read-only
    STATUS      mandatory
    DESCRIPTION
"1400.0010.0001.0008 This attribute defines the BIOS setup control status
of the numeric lock."
    ::= { biosSetUpControlTableEntry 8 }
bSUCnumLockControlName                          OBJECT-TYPE
    SYNTAX      DellString
    ACCESS      read-only
    STATUS      mandatory
    DESCRIPTION
"1400.0010.0001.0009 This attribute defines the BIOS setup control name
of the numeric lock."
    ::= { biosSetUpControlTableEntry 9 }
bSUCprocessorSerialNumberControlCapabilities    OBJECT-TYPE
    SYNTAX      DellStateCapabilities
    ACCESS      read-only
    STATUS      mandatory
    DESCRIPTION
"1400.0010.0001.0010 This attribute defines the BIOS setup control capabilities
of the processor serial number."
    ::= { biosSetUpControlTableEntry 10 }
bSUCprocessorSerialNumberControlSettings        OBJECT-TYPE
    SYNTAX      DellStateSettings
    ACCESS      read-write
    STATUS      mandatory
    DESCRIPTION
"1400.0010.0001.0011 This attribute defines the BIOS setup control settings
of the processor serial number."
    ::= { biosSetUpControlTableEntry 11 }
bSUCprocessorSerialNumberControlStatus          OBJECT-TYPE
    SYNTAX      DellStatus
    ACCESS      read-only
    STATUS      mandatory
    DESCRIPTION
"1400.0010.0001.0012 This attribute defines the BIOS setup control status
of the processor serial number."
    ::= { biosSetUpControlTableEntry 12 }
bSUCprocessorSerialNumberControlName            OBJECT-TYPE
    SYNTAX      DellString
    ACCESS      read-only
    STATUS      mandatory
    DESCRIPTION
"1400.0010.0001.0013 This attribute defines the BIOS setup control name
of the processor serial number."
    ::= { biosSetUpControlTableEntry 13 }
bSUCspeakerControlCapabilitiesUnique            OBJECT-TYPE
    SYNTAX      DellSpeakerControlCapabilitiesUnique
    ACCESS      read-only
    STATUS      mandatory
    DESCRIPTION
"1400.0010.0001.0014 This attribute defines the BIOS setup control capabilities
of the speaker."
    ::= { biosSetUpControlTableEntry 14 }
bSUCspeakerControlSettingsUnique                OBJECT-TYPE
    SYNTAX      DellSpeakerControlSettingsUnique
    ACCESS      read-write
    STATUS      mandatory
    DESCRIPTION
"1400.0010.0001.0015 This attribute defines the BIOS setup control settings
of the speaker."
    ::= { biosSetUpControlTableEntry 15 }
bSUCspeakerControlStatus                        OBJECT-TYPE
    SYNTAX      DellStatus
    ACCESS      read-only
    STATUS      mandatory
    DESCRIPTION
"1400.0010.0001.0016 This attribute defines the BIOS setup control status
of the speaker."
    ::= { biosSetUpControlTableEntry 16 }
bSUCspeakerControlName                          OBJECT-TYPE
    SYNTAX      DellString
    ACCESS      read-only
    STATUS      mandatory
    DESCRIPTION
"1400.0010.0001.0017 This attribute defines the BIOS setup control name
of the speaker."
    ::= { biosSetUpControlTableEntry 17 }
bSUCnIFwakeonLanControlCapabilitiesUnique       OBJECT-TYPE
    SYNTAX      DellNIFwakeonLanControlCapabilitiesUnique
    ACCESS      read-only
    STATUS      mandatory
    DESCRIPTION
"1400.0010.0001.0018 This attribute defines the BIOS setup control capabilities
of the NIF wake on Lan."
    ::= { biosSetUpControlTableEntry 18 }
bSUCnIFwakeonLanControlSettingsUnique           OBJECT-TYPE
    SYNTAX      DellNIFwakeonLanControlSettingsUnique
    ACCESS      read-write
    STATUS      mandatory
    DESCRIPTION
"1400.0010.0001.0019 This attribute defines the BIOS setup control settings
of the NIF wake on Lan."
    ::= { biosSetUpControlTableEntry 19 }
bSUCnIFwakeonLanControlStatus                   OBJECT-TYPE
    SYNTAX      DellStatus
    ACCESS      read-only
    STATUS      mandatory
    DESCRIPTION
"1400.0010.0001.0020 This attribute defines the BIOS setup control status
of the NIF wake on Lan."
    ::= { biosSetUpControlTableEntry 20 }
bSUCnIFwakeonLanControlName                     OBJECT-TYPE
    SYNTAX      DellString
    ACCESS      read-only
    STATUS      mandatory
    DESCRIPTION
"1400.0010.0001.0021 This attribute defines the BIOS setup control name
of the NIF wake on Lan."
    ::= { biosSetUpControlTableEntry 21 }
bSUCbootSequenceControlCapabilitiesUnique       OBJECT-TYPE
    SYNTAX      DellBootSequenceControlCapabilitiesUnique
    ACCESS      read-only
    STATUS      mandatory
    DESCRIPTION
"1400.0010.0001.0022 This attribute defines the BIOS setup control capabilities
of the boot sequence."
    ::= { biosSetUpControlTableEntry 22 }
bSUCbootSequenceControlSettingsUnique           OBJECT-TYPE
    SYNTAX      DellBootSequenceControlSettingsUnique
    ACCESS      read-write
    STATUS      mandatory
    DESCRIPTION
"1400.0010.0001.0023 This attribute defines the BIOS setup control settings
of the boot sequence."
    ::= { biosSetUpControlTableEntry 23 }
bSUCbootSequenceControlStatus                   OBJECT-TYPE
    SYNTAX      DellStatus
    ACCESS      read-only
    STATUS      mandatory
    DESCRIPTION
"1400.0010.0001.0024 This attribute defines the BIOS setup control status
of the boot sequence."
    ::= { biosSetUpControlTableEntry 24 }
bSUCbootSequenceControlName                     OBJECT-TYPE
    SYNTAX      DellString
    ACCESS      read-only
    STATUS      mandatory
    DESCRIPTION
"1400.0010.0001.0025 This attribute defines the BIOS setup control name
of the boot sequence."
    ::= { biosSetUpControlTableEntry 25 }
bSUCadministratorPasswordControlCapabilitiesUnique OBJECT-TYPE
    SYNTAX      DellBIOSPasswordControlCapabilitiesUnique
    ACCESS      read-only
    STATUS      mandatory
    DESCRIPTION
"1400.0010.0001.0026 This attribute defines the BIOS setup control capabilities
of the administrator password."
    ::= { biosSetUpControlTableEntry 26 }
bSUCadministratorPasswordControlSettingsUnique  OBJECT-TYPE
    SYNTAX      DellBIOSPasswordControlSettingsUnique
    ACCESS      read-write
    STATUS      mandatory
    DESCRIPTION
"1400.0010.0001.0027 This attribute defines the BIOS setup control settings
of the administrator password."
    ::= { biosSetUpControlTableEntry 27 }
bSUCadministratorPasswordControlStatus          OBJECT-TYPE
    SYNTAX      DellStatus
    ACCESS      read-only
    STATUS      mandatory
    DESCRIPTION
"1400.0010.0001.0028 This attribute defines the BIOS setup control status
of the administrator password."
    ::= { biosSetUpControlTableEntry 28 }
bSUCadministratorPasswordPasswordVerifyName     OBJECT-TYPE
    SYNTAX      DellString
    ACCESS      read-write
    STATUS      mandatory
    DESCRIPTION
"1400.0010.0001.0029 This attribute defines the BIOS setup control value
of the current administrator password."
    ::= { biosSetUpControlTableEntry 29 }
bSUCadministratorPasswordNewPasswordName        OBJECT-TYPE
    SYNTAX      DellString
    ACCESS      read-write
    STATUS      mandatory
    DESCRIPTION
"1400.0010.0001.0030 This attribute defines the BIOS setup control value
of the new administrator password.  To set a new administrator password,
a successful set of the current administrator password must have been
done immediately preceeding this set."
    ::= { biosSetUpControlTableEntry 30 }
bSUCuserPasswordControlCapabilitiesUnique       OBJECT-TYPE
    SYNTAX      DellBIOSPasswordControlCapabilitiesUnique
    ACCESS      read-only
    STATUS      mandatory
    DESCRIPTION
"1400.0010.0001.0031 This attribute defines the BIOS setup control capabilities
of the user password."
    ::= { biosSetUpControlTableEntry 31 }
bSUCuserPasswordControlSettingsUnique           OBJECT-TYPE
    SYNTAX      DellBIOSPasswordControlSettingsUnique
    ACCESS      read-write
    STATUS      mandatory
    DESCRIPTION
"1400.0010.0001.0032 This attribute defines the BIOS setup control settings
of the user password."
    ::= { biosSetUpControlTableEntry 32 }
bSUCuserPasswordControlStatus                   OBJECT-TYPE
    SYNTAX      DellStatus
    ACCESS      read-only
    STATUS      mandatory
    DESCRIPTION
"1400.0010.0001.0033 This attribute defines the BIOS setup control status
of the user password."
    ::= { biosSetUpControlTableEntry 33 }
bSUCuserPasswordPasswordVerifyName              OBJECT-TYPE
    SYNTAX      DellString
    ACCESS      read-write
    STATUS      mandatory
    DESCRIPTION
"1400.0010.0001.0034 This attribute defines the BIOS setup control value
of the current user password."
    ::= { biosSetUpControlTableEntry 34 }
bSUCuserPasswordNewPasswordName                 OBJECT-TYPE
    SYNTAX      DellString
    ACCESS      read-write
    STATUS      mandatory
    DESCRIPTION
"1400.0010.0001.0035 This attribute defines the BIOS setup control value
of the new user password.  To set a new user password, a successful set of the
current user password must have been done immediately preceeding this set."
    ::= { biosSetUpControlTableEntry 35 }
bSUCtpmSecurityControlCapabilities              OBJECT-TYPE
    SYNTAX      DellTPMSecurityControlCapabilities
    ACCESS      read-only
    STATUS      mandatory
    DESCRIPTION
"1400.0010.0001.0036 This attribute defines the BIOS setup control capabilities
of Trusted Platform Module (TPM) security."
    ::= { biosSetUpControlTableEntry 36 }
bSUCtpmSecurityControlSetting                   OBJECT-TYPE
    SYNTAX      DellTPMSecurityControlSetting
    ACCESS      read-only
    STATUS      mandatory
    DESCRIPTION
"1400.0010.0001.0037 This attribute defines the BIOS setup control setting
of Trusted Platform Module (TPM) security."
    ::= { biosSetUpControlTableEntry 37 }
bSUCtpmSecurityControlStatus                    OBJECT-TYPE
    SYNTAX      DellStatus
    ACCESS      read-only
    STATUS      mandatory
    DESCRIPTION
"1400.0010.0001.0038 This attribute defines the BIOS setup control status
of Trusted Platform Module (TPM) security."
    ::= { biosSetUpControlTableEntry 38 }
bSUCtpmSecurityControlName                      OBJECT-TYPE
    SYNTAX      DellString
    ACCESS      read-only
    STATUS      mandatory
    DESCRIPTION
"1400.0010.0001.0039 This attribute defines the BIOS setup control name
of Trusted Platform Module (TPM) security."
    ::= { biosSetUpControlTableEntry 39 }


-------------------------------------------------------------------------------
-- Small Computer Systems Interface (SCSI) Control Table
--
-- OID Format: 1.3.6.1.4.1.674.10892.1.1400.20.1.<a>.<i1>.<i2>
-------------------------------------------------------------------------------

SCSIControlTableEntry                           ::= SEQUENCE {
    sCSIControlchassisIndex                     DellObjectRange,
    sCSIControlIndex                            DellObjectRange,
    sCSIControlCapabilities                     DellStateCapabilities,
    sCSIControlSettings                         DellStateSettings,
    sCSIControlStatus                           DellStatus,
    sCSIControlName                             DellString
}

sCSIControlTable                                OBJECT-TYPE
    SYNTAX      SEQUENCE OF SCSIControlTableEntry
    ACCESS      not-accessible
    STATUS      mandatory
    DESCRIPTION
"1400.0020 This object defines the Small Computer Systems Interface (SCSI)
Control Table."
    ::= { biosSetUpControlGroup 20 }
sCSIControlTableEntry                           OBJECT-TYPE
    SYNTAX      SCSIControlTableEntry
    ACCESS      not-accessible
    STATUS      mandatory
    DESCRIPTION
"1400.0020.0001 This object defines the Small Computer Systems Interface (SCSI)
Control Table Entry."
    INDEX       { sCSIControlchassisIndex,
                  sCSIControlIndex }
    ::= { sCSIControlTable 1 }

sCSIControlchassisIndex                         OBJECT-TYPE
    SYNTAX      DellObjectRange
    ACCESS      read-only
    STATUS      mandatory
    DESCRIPTION
"1400.0020.0001.0001 This attribute defines the index (one based) of the
assoicated chassis."
    ::= { sCSIControlTableEntry 1 }
sCSIControlIndex                                OBJECT-TYPE
    SYNTAX      DellObjectRange
    ACCESS      read-only
    STATUS      mandatory
    DESCRIPTION
"1400.0020.0001.0002 This attribute defines the index (one based) of the
SCSI control."
    ::= { sCSIControlTableEntry 2 }
sCSIControlCapabilities                         OBJECT-TYPE
    SYNTAX      DellStateCapabilities
    ACCESS      read-only
    STATUS      mandatory
    DESCRIPTION
"1400.0020.0001.0003 This attribute defines the state capabilities of the
SCSI control."
    ::= { sCSIControlTableEntry 3 }
sCSIControlSettings                             OBJECT-TYPE
    SYNTAX      DellStateSettings
    ACCESS      read-write
    STATUS      mandatory
    DESCRIPTION
"1400.0020.0001.0004 This attribute defines the state settings of the
SCSI control."
    ::= { sCSIControlTableEntry 4 }
sCSIControlStatus                               OBJECT-TYPE
    SYNTAX      DellStatus
    ACCESS      read-only
    STATUS      mandatory
    DESCRIPTION
"1400.0020.0001.0005 This attribute defines the status of the
SCSI control."
    ::= { sCSIControlTableEntry 5 }
sCSIControlName                                 OBJECT-TYPE
    SYNTAX      DellString
    ACCESS      read-only
    STATUS      mandatory
    DESCRIPTION
"1400.0020.0001.0006 This attribute defines the BIOS setup control name
of the SCSI device."
    ::= { sCSIControlTableEntry 6 }


-------------------------------------------------------------------------------
-- Parallel Port Control Table
--
-- OID Format: 1.3.6.1.4.1.674.10892.1.1400.30.1.<a>.<i1>.<i2>
-------------------------------------------------------------------------------

DellParallelPortControlCapabilitiesUnique       ::= INTEGER {
    unknown(1),                                 -- parallel port capabilities are unknown
    enableCapable(2),                           -- parallel port can be enabled or disabled
    lpt1Capable(4),                             -- parallel port can be set to LPT1
    lpt1andEnableCapable(6),                    -- parallel port can be enabled and set to LPT1
    lpt2Capable(8),                             -- parallel port can be set to LPT2
    lpt2andEnableCapable(10),                   -- parallel port can be enabled and set to LPT2
    lpt3Capable(16),                            -- parallel port can be set to LPT3
    lpt3andEnableCapable(18),                   -- parallel port can be enabled and set to LPT3
    allParallelPortCapable(30)                  -- parallel port can be enabled and set to LPT1, LPT2 or LPT3
}
DellParallelPortControlSettingsUnique           ::= INTEGER {
    unknown(1),                                 -- parallel port settings are unknown
    enabled(2),                                 -- parallel port enabled
    lpt1(4),                                    -- parallel port set to LPT1
    lpt1Enabled(6),                             -- parallel port enabled and set to LPT1
    lpt2(8),                                    -- parallel port set to LPT2
    lpt2Enabled(10),                            -- parallel port enabled and set to LPT2
    lpt3(16),                                   -- parallel port set to LPT3
    lpt3Enabled(18)                             -- parallel port enabled and set to LPT3
}
DellParallelPortControlModeCapabilitiesUnique   ::= INTEGER {
    unknown(1),                                 -- mode capabilities are unknown
    atCapable(2),                               -- parallel port can be set to AT mode
    ps2Capable(4),                              -- parallel port can be set to PS/2 mode
    atAndPS2Capable(6),                         -- parallel port can be set to AT mode or PS/2 mode
    ecpCapable(8),                              -- parallel port can be set to ECP mode
    eppCapable(16),                             -- parallel port can be set to EPP mode
    allModeCapable(30)                          -- parallel port can be set to all modes
}
DellParallelPortControlModeSettingsUnique       ::= INTEGER {
    unknown(1),                                 -- mode settings are unknown
    atModeEnabled(2),                           -- parallel port set to AT mode
    ps2ModeEnabled(4),                          -- parallel port set to PS/2 mode
    ecpModeEnabled(8),                          -- parallel port set to ECP mode
    eppModeEnabled(16)                          -- parallel port set to EPP mode
}

ParallelPortControlTableEntry                   ::= SEQUENCE {
    parallelPortControlchassisIndex             DellObjectRange,
    parallelPortControlIndex                    DellObjectRange,
    parallelPortControlCapabilitiesUnique       DellParallelPortControlCapabilitiesUnique,
    parallelPortControlSettingsUnique           DellParallelPortControlSettingsUnique,
    parallelPortControlStatus                   DellStatus,
    parallelPortControlName                     DellString,
    parallelPortControlModeCapabilitiesUnique   DellParallelPortControlModeCapabilitiesUnique,
    parallelPortControlModeSettingsUnique       DellParallelPortControlModeSettingsUnique
}

parallelPortControlTable                        OBJECT-TYPE
    SYNTAX      SEQUENCE OF ParallelPortControlTableEntry
    ACCESS      not-accessible
    STATUS      mandatory
    DESCRIPTION
"1400.0030 This object defines the Parallel Port Control Table."
    ::= { biosSetUpControlGroup 30 }
parallelPortControlTableEntry                   OBJECT-TYPE
    SYNTAX      ParallelPortControlTableEntry
    ACCESS      not-accessible
    STATUS      mandatory
    DESCRIPTION
"1400.0030.0001 This object defines the Parallel Port Control Table Entry."
    INDEX       { parallelPortControlchassisIndex,
                  parallelPortControlIndex }
    ::= { parallelPortControlTable 1 }

parallelPortControlchassisIndex                 OBJECT-TYPE
    SYNTAX      DellObjectRange
    ACCESS      read-only
    STATUS      mandatory
    DESCRIPTION
"1400.0030.0001.0001 This attribute defines the index (one based) of the
associated chassis."
    ::= { parallelPortControlTableEntry 1 }
parallelPortControlIndex                        OBJECT-TYPE
    SYNTAX      DellObjectRange
    ACCESS      read-only
    STATUS      mandatory
    DESCRIPTION
"1400.0030.0001.0002 This attribute defines the index (one based) of the
parallel port control."
    ::= { parallelPortControlTableEntry 2 }
parallelPortControlCapabilitiesUnique           OBJECT-TYPE
    SYNTAX      DellParallelPortControlCapabilitiesUnique
    ACCESS      read-only
    STATUS      mandatory
    DESCRIPTION
"1400.0030.0001.0003 This attribute defines the port capabilities of the
parallel port control."
    ::= { parallelPortControlTableEntry 3 }
parallelPortControlSettingsUnique               OBJECT-TYPE
    SYNTAX      DellParallelPortControlSettingsUnique
    ACCESS      read-write
    STATUS      mandatory
    DESCRIPTION
"1400.0030.0001.0004 This attribute defines the port settings of the
parallel port control."
    ::= { parallelPortControlTableEntry 4 }
parallelPortControlStatus                       OBJECT-TYPE
    SYNTAX      DellStatus
    ACCESS      read-only
    STATUS      mandatory
    DESCRIPTION
"1400.0030.0001.0005 This attribute defines the status of the
parallel port control."
    ::= { parallelPortControlTableEntry 5 }
parallelPortControlName                         OBJECT-TYPE
    SYNTAX      DellString
    ACCESS      read-only
    STATUS      mandatory
    DESCRIPTION
"1400.0030.0001.0006 This attribute defines the BIOS setup control name
of the parallel port."
    ::= { parallelPortControlTableEntry 6 }
parallelPortControlModeCapabilitiesUnique       OBJECT-TYPE
    SYNTAX      DellParallelPortControlModeCapabilitiesUnique
    ACCESS      read-only
    STATUS      mandatory
    DESCRIPTION
"1400.0030.0001.0007 This attribute defines the mode capabilities of the
parallel port control."
    ::= { parallelPortControlTableEntry 7 }
parallelPortControlModeSettingsUnique           OBJECT-TYPE
    SYNTAX      DellParallelPortControlModeSettingsUnique
    ACCESS      read-write
    STATUS      mandatory
    DESCRIPTION
"1400.0030.0001.0008 This attribute defines the mode settings of the
parallel port control."
    ::= { parallelPortControlTableEntry 8 }


-------------------------------------------------------------------------------
-- Serial Port Control Table
--
-- OID Format: 1.3.6.1.4.1.674.10892.1.1400.40.1.<a>.<i1>.<i2>
-------------------------------------------------------------------------------

DellSerialPortControlCapabilitiesUnique         ::= INTEGER {
    unknown(1),                                 -- serial port capabilities are unknown
    enableCapable(2),                           -- serial port can be enabled or disabled
    com1Capable(4),                             -- serial port can be set to COM1
    enableAndCom1Capable(6),                    -- serial port can be enabled and set to COM1
    com2Capable(8),                             -- serial port can be set to COM2
    enableAndCom2Capable(10),                   -- serial port can be enabled and set to COM2
    com3Capable(16),                            -- serial port can be set to COM3
    enableAndCom3Capable(18),                   -- serial port can be enabled and set to COM3
    com4Capable(32),                            -- serial port can be set to COM4
    enableAndCom4Capable(34),                   -- serial port can be enabled and set to COM4
    autoConfigCapable(64),                      -- serial port can be autoconfigured
    com1OrCom3CapableAndAutoConfigCapable(86),
    com2OrCom4CapableAndAutoConfigCapable(106),
    allcomCapable(126)                          -- serial port supports all capabilities
}
DellSerialPortControlSettingsUnique             ::= INTEGER {
    unknown(1),                                 -- serial port settings are unknown
    enabled(2),                                 -- serial port enabled
    com1(4),                                    -- serial port set to COM1
    com1Enabled(6),                             -- serial port enabled and set to COM1
    com2(8),                                    -- serial port set to COM2
    com2Enabled(10),                            -- serial port enabled and set to COM2
    com3(16),                                   -- serial port set to COM3
    com3Enabled(18),                            -- serial port enabled and set to COM3
    com4(32),                                   -- serial port set to COM4
    com4Enabled(34),                            -- serial port enabled and set to COM4
    comPortsAutoConfig(64),                     -- serial port set to autoconfiguration
    enabledAndAutoConfig(66)                    -- serial port enabled and set to autoconfiguration
}

SerialPortControlTableEntry                     ::= SEQUENCE {
    serialPortControlchassisIndex               DellObjectRange,
    serialPortControlIndex                      DellObjectRange,
    serialPortControlCapabilitiesUnique         DellSerialPortControlCapabilitiesUnique,
    serialPortControlSettingsUnique             DellSerialPortControlSettingsUnique,
    serialPortControlStatus                     DellStatus,
    serialPortControlName                       DellString
}

serialPortControlTable                  OBJECT-TYPE
    SYNTAX      SEQUENCE OF SerialPortControlTableEntry
    ACCESS      not-accessible
    STATUS      mandatory
    DESCRIPTION
"1400.0040 This object defines the Serial Port Control Table."
    ::= { biosSetUpControlGroup 40 }
serialPortControlTableEntry             OBJECT-TYPE
    SYNTAX      SerialPortControlTableEntry
    ACCESS      not-accessible
    STATUS      mandatory
    DESCRIPTION
"1400.0040.0001 This object defines the Serial Port Control Table Entry."
    INDEX       { serialPortControlchassisIndex,
                  serialPortControlIndex }
    ::= { serialPortControlTable 1 }

serialPortControlchassisIndex               OBJECT-TYPE
    SYNTAX      DellObjectRange
    ACCESS      read-only
    STATUS      mandatory
    DESCRIPTION
"1400.0040.0001.0001 This attribute defines the index (one based) of the
associated chassis."
    ::= { serialPortControlTableEntry 1 }
serialPortControlIndex                  OBJECT-TYPE
    SYNTAX      DellObjectRange
    ACCESS      read-only
    STATUS      mandatory
    DESCRIPTION
"1400.0040.0001.0002 This attribute defines the index (one based) of the
serial port control."
    ::= { serialPortControlTableEntry 2 }
serialPortControlCapabilitiesUnique    OBJECT-TYPE
    SYNTAX      DellSerialPortControlCapabilitiesUnique
    ACCESS      read-only
    STATUS      mandatory
    DESCRIPTION
"1400.0040.0001.0003 This attribute defines the port capabilities of the
serial port control."
    ::= { serialPortControlTableEntry 3 }
serialPortControlSettingsUnique        OBJECT-TYPE
    SYNTAX      DellSerialPortControlSettingsUnique
    ACCESS      read-write
    STATUS      mandatory
    DESCRIPTION
"1400.0040.0001.0004 This attribute defines the port settings of the
serial port control."
    ::= { serialPortControlTableEntry 4 }
serialPortControlStatus        OBJECT-TYPE
    SYNTAX      DellStatus
    ACCESS      read-only
    STATUS      mandatory
    DESCRIPTION
"1400.0040.0001.0005 This attribute defines the status of the
serial port control."
    ::= { serialPortControlTableEntry 5 }
serialPortControlName                  OBJECT-TYPE
    SYNTAX      DellString
    ACCESS      read-only
    STATUS      mandatory
    DESCRIPTION
"1400.0040.0001.0006 This attribute defines the BIOS setup control name
of the serial port."
    ::= { serialPortControlTableEntry 6 }


-------------------------------------------------------------------------------
-- Universal Serial Bus (USB) Control Table
--
-- OID Format: 1.3.6.1.4.1.674.10892.1.1400.50.1.<a>.<i1>.<i2>
-------------------------------------------------------------------------------

UsbControlTableEntry                            ::= SEQUENCE {
    usbControlchassisIndex                      DellObjectRange,
    usbControlIndex                             DellObjectRange,
    usbControlCapabilities                      DellStateCapabilities,
    usbControlSettings                          DellStateSettings,
    usbControlStatus                            DellStatus,
    usbControlName                              DellString
}

usbControlTable                                 OBJECT-TYPE
    SYNTAX      SEQUENCE OF UsbControlTableEntry
    ACCESS      not-accessible
    STATUS      mandatory
    DESCRIPTION
"1400.0050 This object defines the Universal Serial Bus (USB) Control Table."
    ::= { biosSetUpControlGroup 50 }
usbControlTableEntry                            OBJECT-TYPE
    SYNTAX      UsbControlTableEntry
    ACCESS      not-accessible
    STATUS      mandatory
    DESCRIPTION
"1400.0050.0001 This object defines the Universal Serial Bus (USB) Control
Table Entry."
    INDEX       { usbControlchassisIndex,
                  usbControlIndex }
    ::= { usbControlTable 1 }

usbControlchassisIndex                          OBJECT-TYPE
    SYNTAX      DellObjectRange
    ACCESS      read-only
    STATUS      mandatory
    DESCRIPTION
"1400.0050.0001.0001 This attribute defines the index (one based) of the
associated chassis."
    ::= { usbControlTableEntry 1 }
usbControlIndex                                 OBJECT-TYPE
    SYNTAX      DellObjectRange
    ACCESS      read-only
    STATUS      mandatory
    DESCRIPTION
"1400.0050.0001.0002 This attribute defines the index (one based) of the
USB control."
    ::= { usbControlTableEntry 2 }
usbControlCapabilities                          OBJECT-TYPE
    SYNTAX      DellStateCapabilities
    ACCESS      read-only
    STATUS      mandatory
    DESCRIPTION
"1400.0050.0001.0003 This attribute defines the state capabilities of the
USB control."
    ::= { usbControlTableEntry 3 }
usbControlSettings                              OBJECT-TYPE
    SYNTAX      DellStateSettings
    ACCESS      read-write
    STATUS      mandatory
    DESCRIPTION
"1400.0050.0001.0004 This attribute defines the state settings of the
USB control."
    ::= { usbControlTableEntry 4 }
usbControlStatus                                OBJECT-TYPE
    SYNTAX      DellStatus
    ACCESS      read-only
    STATUS      mandatory
    DESCRIPTION
"1400.0050.0001.0005 This attribute defines the status of the USB control."
    ::= { usbControlTableEntry 5 }
usbControlName                                  OBJECT-TYPE
    SYNTAX      DellString
    ACCESS      read-only
    STATUS      mandatory
    DESCRIPTION
"1400.0050.0001.0006 This attribute defines the BIOS setup control name
of the USB device."
    ::= { usbControlTableEntry 6 }


-------------------------------------------------------------------------------
-- Integrated Device Electronics (IDE) Control Table
--
-- OID Format: 1.3.6.1.4.1.674.10892.1.1400.60.1.<a>.<i1>.<i2>
-------------------------------------------------------------------------------

DellideControlCapabilitiesUnique                ::= INTEGER {
    unknown(1),                                 -- IDE capabilities are unknown
    ideControlAutoConfigOrEnableCapable(2)      -- IDE can be autoconfigured or enabled/disabled
}
DellideControlSettingsUnique                    ::= INTEGER {
    unknown(1),                                 -- IDE settings are unknown
    ideControlAutoConfigEnabledOrEnabled(2)     -- IDE set to autoconfigured or enabled
}

IdeControlTableEntry                            ::= SEQUENCE {
    ideControlchassisIndex                      DellObjectRange,
    ideControlIndex                             DellObjectRange,
    ideControlCapabilitiesUnique                DellideControlCapabilitiesUnique,
    ideControlSettingsUnique                    DellideControlSettingsUnique,
    ideControlStatus                            DellStatus,
    ideControlName                              DellString
}

ideControlTable                                 OBJECT-TYPE
    SYNTAX      SEQUENCE OF IdeControlTableEntry
    ACCESS      not-accessible
    STATUS      mandatory
    DESCRIPTION
"1400.0060 This object defines the Integrated Device Electronics (IDE)
Control Table."
    ::= { biosSetUpControlGroup 60 }
ideControlTableEntry                            OBJECT-TYPE
    SYNTAX      IdeControlTableEntry
    ACCESS      not-accessible
    STATUS      mandatory
    DESCRIPTION
"1400.0060.0001 This object defines the Integrated Device Electronics (IDE)
Control Table Entry."
    INDEX       { ideControlchassisIndex,
                  ideControlIndex }
    ::= { ideControlTable 1 }

ideControlchassisIndex                          OBJECT-TYPE
    SYNTAX      DellObjectRange
    ACCESS      read-only
    STATUS      mandatory
    DESCRIPTION
"1400.0060.0001.0001 This attribute defines the index (one based) of the
associated chassis."
    ::= { ideControlTableEntry 1 }
ideControlIndex                                 OBJECT-TYPE
    SYNTAX      DellObjectRange
    ACCESS      read-only
    STATUS      mandatory
    DESCRIPTION
"1400.0060.0001.0002 This attribute defines the index (one based) of the
IDE control."
    ::= { ideControlTableEntry 2 }
ideControlCapabilitiesUnique                    OBJECT-TYPE
    SYNTAX      DellideControlCapabilitiesUnique
    ACCESS      read-only
    STATUS      mandatory
    DESCRIPTION
"1400.0060.0001.0003 This attribute defines the capabilities of the
IDE control."
    ::= { ideControlTableEntry 3 }
ideControlSettingsUnique                        OBJECT-TYPE
    SYNTAX      DellideControlSettingsUnique
    ACCESS      read-write
    STATUS      mandatory
    DESCRIPTION
"1400.0060.0001.0004 This attribute defines the settings of the
IDE control."
    ::= { ideControlTableEntry 4 }
ideControlStatus                                OBJECT-TYPE
    SYNTAX      DellStatus
    ACCESS      read-only
    STATUS      mandatory
    DESCRIPTION
"1400.0060.0001.0005 This attribute defines the state of the IDE control."
    ::= { ideControlTableEntry 5 }
ideControlName                                  OBJECT-TYPE
    SYNTAX      DellString
    ACCESS      read-only
    STATUS      mandatory
    DESCRIPTION
"1400.0060.0001.0006 This attribute defines the BIOS setup control name
of the IDE device."
    ::= { ideControlTableEntry 6 }


-------------------------------------------------------------------------------
-- Diskette Control Table
--
-- OID Format: 1.3.6.1.4.1.674.10892.1.1400.70.1.<a>.<i1>.<i2>
-------------------------------------------------------------------------------

DellDisketteControlCapabilitiesUnique           ::= INTEGER {
    unknown(1),                                 -- diskette capabilities are unknown
    disketteAutoConfigOrEnableCapable(2),       -- diskette can be enabled or disabled
    disketteReadOnlyCapable(4),                 -- diskette can be set to read only
    disketteAutoConfigOrEnableCapableandReadOnlyCapable(6)
}
DellDisketteControlSettingsUnique               ::= INTEGER {
    unknown(1),                                 -- Diskette Control state is unknown
    disketteAutoConfigEnabledOrEnabled(2),      -- Diskette Control is autoconfigurable or enabled
    disketteisReadOnly(4)                       -- Diskette is in read only operation
}

DisketteControlTableEntry                       ::= SEQUENCE {
    disketteControlchassisIndex                 DellObjectRange,
    disketteControlIndex                        DellObjectRange,
    disketteControlCapabilitiesUnique           DellDisketteControlCapabilitiesUnique,
    disketteControlSettingsUnique               DellDisketteControlSettingsUnique,
    disketteControlStatus                       DellStatus,
    disketteControlName                         DellString
}

disketteControlTable                            OBJECT-TYPE
    SYNTAX      SEQUENCE OF DisketteControlTableEntry
    ACCESS      not-accessible
    STATUS      mandatory
    DESCRIPTION
"1400.0070 This object defines the Diskette Control Table."
    ::= { biosSetUpControlGroup 70 }
disketteControlTableEntry                       OBJECT-TYPE
    SYNTAX      DisketteControlTableEntry
    ACCESS      not-accessible
    STATUS      mandatory
    DESCRIPTION
"1400.0070.0001 This object defines the Diskette Control Table Entry."
    INDEX       { disketteControlchassisIndex,
                  disketteControlIndex }
    ::= { disketteControlTable 1 }

disketteControlchassisIndex                     OBJECT-TYPE
    SYNTAX      DellObjectRange
    ACCESS      read-only
    STATUS      mandatory
    DESCRIPTION
"1400.0070.0001.0001 This attribute defines the index (one based) of the
associated chassis."
    ::= { disketteControlTableEntry 1 }
disketteControlIndex                            OBJECT-TYPE
    SYNTAX      DellObjectRange
    ACCESS      read-only
    STATUS      mandatory
    DESCRIPTION
"1400.0070.0001.0002 This attribute defines the index (one based) of the
diskette control."
    ::= { disketteControlTableEntry 2 }
disketteControlCapabilitiesUnique               OBJECT-TYPE
    SYNTAX      DellDisketteControlCapabilitiesUnique
    ACCESS      read-only
    STATUS      mandatory
    DESCRIPTION
"1400.0070.0001.0003 This attribute defines the capabilities of the
diskette control."
    ::= { disketteControlTableEntry 3 }
disketteControlSettingsUnique                   OBJECT-TYPE
    SYNTAX      DellDisketteControlSettingsUnique
    ACCESS      read-write
    STATUS      mandatory
    DESCRIPTION
"1400.0070.0001.0004 This attribute defines the settings of the
diskette control."
    ::= { disketteControlTableEntry 4 }
disketteControlStatus                           OBJECT-TYPE
    SYNTAX      DellStatus
    ACCESS      read-only
    STATUS      mandatory
    DESCRIPTION
"1400.0070.0001.0005 This attribute defines the status of the
diskette control."
    ::= { disketteControlTableEntry 5 }
disketteControlName                             OBJECT-TYPE
    SYNTAX      DellString
    ACCESS      read-only
    STATUS      mandatory
    DESCRIPTION
"1400.0070.0001.0006 This attribute defines the BIOS setup control name
of the diskette device."
    ::= { disketteControlTableEntry 6 }


-------------------------------------------------------------------------------
-- Network Interface Control Table
--
-- OID Format: 1.3.6.1.4.1.674.10892.1.1400.80.1.<a>.<i1>.<i2>
-------------------------------------------------------------------------------

DellNetworkInterfaceControlCapabilitiesUnique   ::= INTEGER {
    unknown(1),                                 -- network interface capabilities are unknown
    enableCapable(2),                           -- network interface can be enabled or disabled
    enableWithoutPXECapable(4)                  -- network interface can be enabled without PXE
}
DellNetworkInterfaceControlSettingsUnique       ::= INTEGER {
    unknown(1),                                 -- network interface settings are unknown
    enabled(2),                                 -- network interface enabled
    enabledWithoutPXE(4)                        -- network interface enabled without PXE
}

NetworkInterfaceControlTableEntry               ::= SEQUENCE {
    networkInterfaceControlchassisIndex         DellObjectRange,
    networkInterfaceControlIndex                DellObjectRange,
    networkInterfaceControlCapabilitiesUnique   DellNetworkInterfaceControlCapabilitiesUnique,
    networkInterfaceControlSettingsUnique       DellNetworkInterfaceControlSettingsUnique,
    networkInterfaceControlStatus               DellStatus,
    networkInterfaceControlName                 DellString
}

networkInterfaceControlTable                    OBJECT-TYPE
    SYNTAX      SEQUENCE OF NetworkInterfaceControlTableEntry
    ACCESS      not-accessible
    STATUS      mandatory
    DESCRIPTION
"1400.0080 This object defines the Network Interface Control Table."
    ::= { biosSetUpControlGroup 80 }
networkInterfaceControlTableEntry               OBJECT-TYPE
    SYNTAX      NetworkInterfaceControlTableEntry
    ACCESS      not-accessible
    STATUS      mandatory
    DESCRIPTION
"1400.0080.0001 This object defines the Network Interface Control Table Entry."
    INDEX       { networkInterfaceControlchassisIndex,
                  networkInterfaceControlIndex }
    ::= { networkInterfaceControlTable 1 }

networkInterfaceControlchassisIndex             OBJECT-TYPE
    SYNTAX      DellObjectRange
    ACCESS      read-only
    STATUS      mandatory
    DESCRIPTION
"1400.0080.0001.0001 This attribute defines the index (one based) of the
associated chassis."
    ::= { networkInterfaceControlTableEntry 1 }
networkInterfaceControlIndex                    OBJECT-TYPE
    SYNTAX      DellObjectRange
    ACCESS      read-only
    STATUS      mandatory
    DESCRIPTION
"1400.0080.0001.0002 This attribute defines the index (one based) of the
network interface control."
    ::= { networkInterfaceControlTableEntry 2 }
networkInterfaceControlCapabilitiesUnique       OBJECT-TYPE
    SYNTAX      DellNetworkInterfaceControlCapabilitiesUnique
    ACCESS      read-only
    STATUS      mandatory
    DESCRIPTION
"1400.0080.0001.0003 This attribute defines the capabilities of the
network interface control."
    ::= { networkInterfaceControlTableEntry 3 }
networkInterfaceControlSettingsUnique           OBJECT-TYPE
    SYNTAX      DellNetworkInterfaceControlSettingsUnique
    ACCESS      read-write
    STATUS      mandatory
    DESCRIPTION
"1400.0080.0001.0004 This attribute defines the settings of the
network interface control."
    ::= { networkInterfaceControlTableEntry 4 }
networkInterfaceControlStatus                   OBJECT-TYPE
    SYNTAX      DellStatus
    ACCESS      read-only
    STATUS      mandatory
    DESCRIPTION
"1400.0080.0001.0005 This attribute defines the status of the
network interface control."
    ::= { networkInterfaceControlTableEntry 5 }
networkInterfaceControlName                     OBJECT-TYPE
    SYNTAX      DellString
    ACCESS      read-write
    STATUS      mandatory
    DESCRIPTION
"1400.0080.0001.0006 This attribute defines the BIOS setup control name
of the network interface."
    ::= { networkInterfaceControlTableEntry 6 }


-------------------------------------------------------------------------------
-- Local Response Agent (LRA) Group
--
-- OID Format: 1.3.6.1.4.1.674.10892.1.1500
-------------------------------------------------------------------------------


-------------------------------------------------------------------------------
-- Local Response Agent (LRA) Global Settings Table
--
-- OID Format: 1.3.6.1.4.1.674.10892.1.1500.10.1.<a>.<i1>
-------------------------------------------------------------------------------

DellLocalResponseAgentCapabilitiesUnique        ::= INTEGER {
    -- If set to 0 (zero), LRA has no capabilities
    speakerControlCapable(1),                   -- LRA capable of speaker beep
    consoleAlertCapable(2),                     -- LRA capable of console alert
    broadcastMessageCapable(4),                 -- LRA capable of broadcast message
    osShutDownCapable(8),                       -- LRA capable of operating system shutdown
    rebootCapable(16),                          -- LRA capable of system reboot
    powerCycleCapable(32),                      -- LRA capable of system power cycle
    powerOFFCapable(64),                        -- LRA capable of system power off
    executeApplicationCapable(256),             -- LRA capable of executing user-specified application
    lraFullyCapable(383)                        -- all LRA capabilities
}
DellLRAThermalShutdownCapabilitiesUnique        ::= INTEGER {
    -- If set to 0 (zero), LRA has no thermal shutdown capabilities
    unknownCapabilities(1),                     -- thermal shutdown capabilities are unknown
    enableCapable(2),                           -- thermal shutdown can be enabled or disabled
    warningCapable(4),                          -- thermal shutdown can be set to activate on warning
    enableOnWarningCapable(6),
    failureCapable(8),                          -- thermal shutdown can be set to activate on failure
    enableOnFailureCapable(10),
    enableOnWarningOrFailureCapable(14)
}
DellLRAThermalShutdownStateSettingsUnique       ::= INTEGER {
    -- If set to 0 (zero), LRA thermal shutdown is disabled
    unknown(1),                                 -- thermal shutdown settings are unknown
    activatedOnWarning(6),                      -- thermal shutdown set to activate on warning
    activatedOnFailure(10)                      -- thermal shutdown set to activate on failure
}

LRAGlobalSettingsTableEntry                     ::= SEQUENCE {
    lRAGlobalchassisIndex                       DellObjectRange,
    lRAGlobalState                              DellStateSettings,
    lRAGlobalSettingsDisableTimeoutValue        DellUnsigned32BitRange,
    lRAGlobalSettingsCapabilitiesUnique         DellLocalResponseAgentCapabilitiesUnique,
    lRAGlobalThermalShutdownCapabilitiesUnique  DellLRAThermalShutdownCapabilitiesUnique,
    lRAGlobalThermalShutdownStateSettingsUnique DellLRAThermalShutdownStateSettingsUnique
}

lRAGlobalSettingsTable                          OBJECT-TYPE
    SYNTAX      SEQUENCE OF LRAGlobalSettingsTableEntry
    ACCESS      not-accessible
    STATUS      mandatory
    DESCRIPTION
"1500.0010 This object defines the Local Response Agent (LRA) Global Settings
Table."
    ::= { lraGroup 10 }
lRAGlobalSettingsTableEntry                     OBJECT-TYPE
    SYNTAX      LRAGlobalSettingsTableEntry
    ACCESS      not-accessible
    STATUS      mandatory
    DESCRIPTION
"1500.0010.0001 This object defines the Local Response Agent (LRA) Global
Settings Table Entry."
    INDEX       { lRAGlobalchassisIndex }
    ::= { lRAGlobalSettingsTable 1 }

lRAGlobalchassisIndex                           OBJECT-TYPE
    SYNTAX      DellObjectRange
    ACCESS      read-only
    STATUS      mandatory
    DESCRIPTION
"1500.0010.0001.0001 This attribute defines the index (one based) of the
associated chassis."
    ::= { lRAGlobalSettingsTableEntry 1 }
lRAGlobalState                                  OBJECT-TYPE
    SYNTAX     DellStateSettings
    ACCESS      read-only
    STATUS      mandatory
    DESCRIPTION
"1500.0010.0001.0002 This attribute defines the state settings of the
Local Response Agent."
    ::= { lRAGlobalSettingsTableEntry 2 }
lRAGlobalSettingsDisableTimeoutValue            OBJECT-TYPE
    SYNTAX      DellUnsigned32BitRange
    ACCESS      read-only
    STATUS      mandatory
    DESCRIPTION
"1500.0010.0001.0003 This attribute defines the timeout duration in seconds
that the Local Response Agent will be disabled after a machine shutdown and
reboot."
    ::= { lRAGlobalSettingsTableEntry 3 }
lRAGlobalSettingsCapabilitiesUnique             OBJECT-TYPE
    SYNTAX      DellLocalResponseAgentCapabilitiesUnique
    ACCESS      read-only
    STATUS      mandatory
    DESCRIPTION
"1500.0010.0001.0004 This attribute defines the global settings capabilities 
that all Local Response Agents may or may not allow to be set or reset."
    ::= { lRAGlobalSettingsTableEntry 4 }
lRAGlobalThermalShutdownCapabilitiesUnique      OBJECT-TYPE
    SYNTAX      DellLRAThermalShutdownCapabilitiesUnique
    ACCESS      read-only
    STATUS      mandatory
    DESCRIPTION
"1500.0010.0001.0005 This attribute defines the thermal shutdown capabilities 
of the Local Response Agent."
    ::= { lRAGlobalSettingsTableEntry 5 }
lRAGlobalThermalShutdownStateSettingsUnique     OBJECT-TYPE
    SYNTAX      DellLRAThermalShutdownStateSettingsUnique
    ACCESS      read-write
    STATUS      mandatory
    DESCRIPTION
"1500.0010.0001.0006 This attribute defines the thermal shutdown settings 
of the Local Response Agent."
    ::= { lRAGlobalSettingsTableEntry 6 }


-------------------------------------------------------------------------------
-- Local Response Agent (LRA) Action Table
--
-- OID Format: 1.3.6.1.4.1.674.10892.1.1500.20.1.<a>.<i1>.<i2>
-------------------------------------------------------------------------------

DellLocalResponseAgentSettingsUnique            ::= INTEGER {
    speakerControl(1),                          -- issue speaker beep
    consoleAlert(2),                            -- issue console alert
    broadcastMessage(4),                        -- issue broadcast message
    osShutDown(8),                              -- issue operating system shutdown
    reboot(16),                                 -- issue system reboot
    powerCycle(32),                             -- issue system power cycle
    powerOFF(64),                               -- issue system power off
    executeApplication(256),                    -- execute user-specified application
    allLRASettingsUnique(383)                   -- all LRA settings
}

LRAActionTableTableEntry                        ::= SEQUENCE {
    lRAActionTablechassisIndex                  DellObjectRange,
    lRAActionTableActionNumberIndex             DellUnsigned16BitRange,
    lRAActionTableUserApplicationName           DisplayString (SIZE (0..256)),
    lRAActionTableSettingsUnique                DellLocalResponseAgentSettingsUnique
}

lRAActionTableTable                             OBJECT-TYPE
    SYNTAX      SEQUENCE OF LRAActionTableTableEntry
    ACCESS      not-accessible
    STATUS      mandatory
    DESCRIPTION
"1500.0020 This object defines the Local Response Agent (LRA) Action Table."
    ::= { lraGroup 20 }
lRAActionTableTableEntry                        OBJECT-TYPE
    SYNTAX      LRAActionTableTableEntry
    ACCESS      not-accessible
    STATUS      mandatory
    DESCRIPTION
"1500.0020.0001 This object defines the Local Response Agent (LRA) Action
Table Entry."
    INDEX       { lRAActionTablechassisIndex,
                  lRAActionTableActionNumberIndex }
    ::= { lRAActionTableTable 1 }

lRAActionTablechassisIndex                      OBJECT-TYPE
    SYNTAX      DellObjectRange
    ACCESS      read-only
    STATUS      mandatory
    DESCRIPTION
"1500.0020.0001.0001 This attribute defines the index (one based) of the
associated chassis."
    ::= { lRAActionTableTableEntry 1 }
lRAActionTableActionNumberIndex                 OBJECT-TYPE
    SYNTAX      DellUnsigned16BitRange
    ACCESS      read-only
    STATUS      mandatory
    DESCRIPTION
"1500.0020.0001.0002 This attribute defines the action number index
of the LRA action. The currently supported values are:
    160  temperature failure action definition
    168  cooling device failure action definition
    172  voltage failure action definition
    200  temperature warning action definition
    202  voltage warning action definition
    204  cooling device warning action definition
    206  amperage failure action definition
    208  amperage warning action definition
    210  redundancy unit redundancy lost action definition
    212  redundancy unit redundancy degraded action definition
    214  power supply failure action definition
    220  chassis intrusion action definition
    228  memory device noncritical action definition
    474  memory device critical action definition
    1006 automatic system recovery (ASR) action definition
    1353 power supply warning action definition
    1553 log near full action definition
    1554 log full action definition
    1603 processor warning action definition
    1604 processor failure action definition
    1703 battery warning action definition
    1704 battery failure action definition"
    ::= { lRAActionTableTableEntry 2 }
lRAActionTableUserApplicationName               OBJECT-TYPE
    SYNTAX      DisplayString (SIZE (0..256))
    ACCESS      read-write
    STATUS      mandatory
    DESCRIPTION
"1500.0020.0001.0003 This attribute defines the name of the user application
executable path and file name to execute by the Local Response Agent if the
value executeApplication was set."
    ::= { lRAActionTableTableEntry 3 }
lRAActionTableSettingsUnique                    OBJECT-TYPE
    SYNTAX      DellLocalResponseAgentSettingsUnique
    ACCESS      read-write
    STATUS      mandatory
    DESCRIPTION
"1500.0020.0001.0004 This attribute defines the settings for the LRA action."
    ::= { lRAActionTableTableEntry 4 }


-------------------------------------------------------------------------------
-- Cost Of Ownership (COO) Group
--
-- OID Format: 1.3.6.1.4.1.674.10892.1.1600
-------------------------------------------------------------------------------


DellCooOwnershipCodes                           ::= INTEGER {
    other(1),                                   -- ownership code is other than following values
    unknown(2),                                 -- ownership code is unknown
    owned(3),                                   -- ownership code is owned
    leased(4),                                  -- ownership code is leased
    rented(5),                                  -- ownership code is rented
    offOfLease(6),                              -- ownership code is off of lease
    transfer(7)                                 -- ownership code is transfer
}
DellCooHourDayDurationType                      ::= INTEGER {
    unknown(1),                                 -- duration type is unknown
    hours(2),                                   -- duration type is hours
    days(3)                                     -- duration type is days
}
DellCooDayMonthDurationType                     ::= INTEGER {
    unknown(1),                                 -- duration type is unknown
    days(3),                                    -- duration type is days
    months(4)                                   -- duration type is months
}
DellCooMonthYearDurationType                    ::= INTEGER {
    unknown(1),                                 -- duration type is unknown
    months(4),                                  -- duration type is months
    years(5)                                    -- duration type is years
}


-------------------------------------------------------------------------------
-- Cost Of Ownership (COO) Table
--
-- OID Format: 1.3.6.1.4.1.674.10892.1.1600.10.1.<a>.<i1>
-------------------------------------------------------------------------------

CooTableEntry                                   ::= SEQUENCE {
    coochassisIndex                             DellObjectRange,
    cooState                                    DellStateSettings,
    cooAquisitionPurchaseCost                   DellUnsigned32BitRange,
    cooAquisitionWayBillNumber                  DellUnsigned32BitRange,
    cooAquisitionInstallDateName                DellDateName,
    cooAquisitionPurchaseOrder                  DellUnsigned32BitRange,
    cooAquisitionPurchaseDateName               DellDateName,
    cooAquisitionSigningAuthorityName           DellCostofOwnershipString,
    cooOriginalMachineConfigurationExpensed     DellBoolean,
    cooOriginalMachineConfigurationVendorName   DellCostofOwnershipString,
    cooCostCenterInformationVendorName          DellCostofOwnershipString,
    cooUserInformationUserName                  DellCostofOwnershipString,
    cooExtendedWarrantyStartDateName            DellDateName,
    cooExtendedWarrantyEndDateName              DellDateName,
    cooExtendedWarrantyCost                     DellUnsigned32BitRange,
    cooExtendedWarrantyProviderName             DellCostofOwnershipString,
    cooOwnershipCode                            DellCooOwnershipCodes,
    cooCorporateOwnerName                       DellCostofOwnershipString,
    cooHazardousWasteCodeName                   DellCostofOwnershipString,
    cooDeploymentDateLength                     DellUnsigned32BitRange,
    cooDeploymentDurationType                   DellCooHourDayDurationType,
    cooTrainingName                             DellCostofOwnershipString,
    cooOutsourcingProblemDescriptionName        DellCostofOwnershipString,
    cooOutsourcingServiceFeeName                DellCostofOwnershipString,
    cooOutsourcingSigningAuthorityName          DellCostofOwnershipString,
    cooOutsourcingProviderFeeName               DellCostofOwnershipString,
    cooOutsourcingProviderServiceLevelName      DellCostofOwnershipString,
    cooInsuranceCompanyName                     DellCostofOwnershipString,
    cooBoxAssetTagName                          DellCostofOwnershipString,
    cooBoxSystemName                            DellCostofOwnershipString,
    cooBoxCPUSerialNumberName                   DellCostofOwnershipString,
    cooOperatingSystemUpgradeTypeName           DellCostofOwnershipString,
    cooOperatingSystemUpgradePatchLevelName     DellCostofOwnershipString,
    cooOperatingSystemUpgradeDate               DellCostofOwnershipString,
    cooDepreciationDuration                     DellUnsigned32BitRange,
    cooDepreciationDurationType                 DellCooMonthYearDurationType,
    cooDepreciationPercentage                   DellUnsigned32BitRange,
    cooDepreciationMethodName                   DellCostofOwnershipString,
    cooRegistrationIsRegistered                 DellBoolean
}

cooTable                                        OBJECT-TYPE
    SYNTAX      SEQUENCE OF CooTableEntry
    ACCESS      not-accessible
    STATUS      mandatory
    DESCRIPTION
"1600.0010 This object defines the Cost Of Ownership (COO) Table."
    ::= { cooGroup 10 }
cooTableEntry                                   OBJECT-TYPE
    SYNTAX      CooTableEntry
    ACCESS      not-accessible
    STATUS      mandatory
    DESCRIPTION
"1600.0010.0001 This object defines the Cost Of Ownership (COO) Table Entry."
    INDEX       { coochassisIndex }
    ::= { cooTable 1 }

coochassisIndex                                 OBJECT-TYPE
    SYNTAX      DellObjectRange
    ACCESS      read-only
    STATUS      mandatory
    DESCRIPTION
"1600.0010.0001.0001 This attribute defines the index (one based) of the
associated chassis."
    ::= { cooTableEntry 1 }
cooState                                        OBJECT-TYPE
    SYNTAX      DellStateSettings
    ACCESS      read-only
    STATUS      mandatory
    DESCRIPTION
"1600.0010.0001.0002 This attribute defines the state settings of the
COO information."
    ::= { cooTableEntry 2 }
cooAquisitionPurchaseCost                       OBJECT-TYPE
    SYNTAX      DellUnsigned32BitRange
    ACCESS      read-write
    STATUS      mandatory
    DESCRIPTION
"1600.0010.0001.0003 This attribute defines the purchase cost of the system."
    ::= { cooTableEntry 3 }
cooAquisitionWayBillNumber                      OBJECT-TYPE
    SYNTAX      DellUnsigned32BitRange
    ACCESS      read-write
    STATUS      mandatory
    DESCRIPTION
"1600.0010.0001.0004 This attribute defines the waybill number of the system."
    ::= { cooTableEntry 4 }
cooAquisitionInstallDateName                    OBJECT-TYPE
    SYNTAX      DellDateName
    ACCESS      read-write
    STATUS      mandatory
    DESCRIPTION
"1600.0010.0001.0005 This attribute defines the install date and time of the
system.  Dates are defined in the ASCII format:
    yyyyMMddhhmmss.uuuuuu+fff or yyyyMMddhhmmss.uuuuuu-fff
where yyyy is the year, MM is the month, dd is the day, hh are the hours,
mm are the minutes, ss are the seconds, uuuuuu are the microseconds and
+fff or -fff is the offset from UTC in minutes."
    ::= { cooTableEntry 5 }
cooAquisitionPurchaseOrder                      OBJECT-TYPE
    SYNTAX      DellUnsigned32BitRange
    ACCESS      read-write
    STATUS      mandatory
    DESCRIPTION
"1600.0010.0001.0006 This attribute defines the purchase order number of the
system."
    ::= { cooTableEntry 6 }
cooAquisitionPurchaseDateName                   OBJECT-TYPE
    SYNTAX      DellDateName
    ACCESS      read-write
    STATUS      mandatory
    DESCRIPTION
"1600.0010.0001.0007 This attribute defines the purchase date and time of the
system.  Dates are defined in the ASCII format:
    yyyyMMddhhmmss.uuuuuu+fff or yyyyMMddhhmmss.uuuuuu-fff
where yyyy is the year, MM is the month, dd is the day, hh are the hours,
mm are the minutes, ss are the seconds, uuuuuu are the microseconds and
+fff or -fff is the offset from UTC in minutes."
    ::= { cooTableEntry 7 }
cooAquisitionSigningAuthorityName               OBJECT-TYPE
    SYNTAX      DellCostofOwnershipString
    ACCESS      read-write
    STATUS      mandatory
    DESCRIPTION
"1600.0010.0001.0008 This attribute defines the name of the signing authority
for the system."
    ::= { cooTableEntry 8 }
cooOriginalMachineConfigurationExpensed         OBJECT-TYPE
    SYNTAX      DellBoolean
    ACCESS      read-write
    STATUS      mandatory
    DESCRIPTION
"1600.0010.0001.0009 This attribute defines if the purchase of the system
was expensed or not."
    ::= { cooTableEntry 9 }
cooOriginalMachineConfigurationVendorName       OBJECT-TYPE
    SYNTAX      DellCostofOwnershipString
    ACCESS      read-only
    STATUS      mandatory
    DESCRIPTION
"1600.0010.0001.0010 This attribute defines the name of the vendor of the
system."
    ::= { cooTableEntry 10 }
cooCostCenterInformationVendorName              OBJECT-TYPE
    SYNTAX      DellCostofOwnershipString
    ACCESS      read-write
    STATUS      mandatory
    DESCRIPTION
"1600.0010.0001.0011 This attribute defines the cost center name of the
system."
    ::= { cooTableEntry 11 }
cooUserInformationUserName                      OBJECT-TYPE
    SYNTAX      DellCostofOwnershipString
    ACCESS      read-write
    STATUS      mandatory
    DESCRIPTION
"1600.0010.0001.0012 This attribute defines the name of the user of the
system."
    ::= { cooTableEntry 12 }
cooExtendedWarrantyStartDateName                OBJECT-TYPE
    SYNTAX      DellDateName
    ACCESS      read-write
    STATUS      mandatory
    DESCRIPTION
"1600.0010.0001.0013 This attribute defines the extended warranty start date
and time for the system.  Dates are defined in the ASCII format:
    yyyyMMddhhmmss.uuuuuu+fff or yyyyMMddhhmmss.uuuuuu-fff
where yyyy is the year, MM is the month, dd is the day, hh are the hours,
mm are the minutes, ss are the seconds, uuuuuu are the microseconds and
+fff or -fff is the offset from UTC in minutes."
    ::= { cooTableEntry 13 }
cooExtendedWarrantyEndDateName                  OBJECT-TYPE
    SYNTAX      DellDateName
    ACCESS      read-write
    STATUS      mandatory
    DESCRIPTION
"1600.0010.0001.0014 This attribute defines the extended warranty end date
and time for the system.  Dates are defined in the ASCII format:
    yyyyMMddhhmmss.uuuuuu+fff or yyyyMMddhhmmss.uuuuuu-fff
where yyyy is the year, MM is the month, dd is the day, hh are the hours,
mm are the minutes, ss are the seconds, uuuuuu are the microseconds and
+fff or -fff is the offset from UTC in minutes."
    ::= { cooTableEntry 14 }
cooExtendedWarrantyCost                         OBJECT-TYPE
    SYNTAX      DellUnsigned32BitRange
    ACCESS      read-write
    STATUS      mandatory
    DESCRIPTION
"1600.0010.0001.0015 This attribute defines the extended warranty cost
for the system."
    ::= { cooTableEntry 15 }
cooExtendedWarrantyProviderName                 OBJECT-TYPE
    SYNTAX      DellCostofOwnershipString
    ACCESS      read-write
    STATUS      mandatory
    DESCRIPTION
"1600.0010.0001.0016 This attribute defines the name of the extended warranty
provider for the system."
    ::= { cooTableEntry 16 }
cooOwnershipCode                                OBJECT-TYPE
    SYNTAX      DellCooOwnershipCodes
    ACCESS      read-write
    STATUS      mandatory
    DESCRIPTION
"1600.0010.0001.0017 This attribute defines the ownership code for the system."
    ::= { cooTableEntry 17 }
cooCorporateOwnerName                           OBJECT-TYPE
    SYNTAX      DellCostofOwnershipString
    ACCESS      read-write
    STATUS      mandatory
    DESCRIPTION
"1600.0010.0001.0018 This attribute defines the name of the corporate owner
of the system."
    ::= { cooTableEntry 18 }
cooHazardousWasteCodeName                       OBJECT-TYPE
    SYNTAX      DellCostofOwnershipString
    ACCESS      read-write
    STATUS      mandatory
    DESCRIPTION
"1600.0010.0001.0019 This attribute defines the hazardous waste code name
for the system."
    ::= { cooTableEntry 19 }
cooDeploymentDateLength                         OBJECT-TYPE
    SYNTAX      DellUnsigned32BitRange
    ACCESS      read-write
    STATUS      mandatory
    DESCRIPTION
"1600.0010.0001.0020 This attribute defines the deployment time length
for the system."
    ::= { cooTableEntry 20 }
cooDeploymentDurationType                       OBJECT-TYPE
    SYNTAX      DellCooHourDayDurationType
    ACCESS      read-write
    STATUS      mandatory
    DESCRIPTION
"1600.0010.0001.0021 This attribute defines the deployment duration time unit
for the Dell System."
    ::= { cooTableEntry 21 }
cooTrainingName                                 OBJECT-TYPE
    SYNTAX      DellCostofOwnershipString
    ACCESS      read-write
    STATUS      mandatory
    DESCRIPTION
"1600.0010.0001.0022 This attribute defines the training name for the system."
    ::= { cooTableEntry 22 }
cooOutsourcingProblemDescriptionName            OBJECT-TYPE
    SYNTAX      DellCostofOwnershipString
    ACCESS      read-write
    STATUS      mandatory
    DESCRIPTION
"1600.0010.0001.0023 This attribute defines the outsourcing problem description
for the system."
    ::= { cooTableEntry 23 }
cooOutsourcingServiceFeeName                    OBJECT-TYPE
    SYNTAX      DellCostofOwnershipString
    ACCESS      read-write
    STATUS      mandatory
    DESCRIPTION
"1600.0010.0001.0024 This attribute defines the outsourcing service fee
for the system."
    ::= { cooTableEntry 24 }
cooOutsourcingSigningAuthorityName              OBJECT-TYPE
    SYNTAX      DellCostofOwnershipString
    ACCESS      read-write
    STATUS      mandatory
    DESCRIPTION
"1600.0010.0001.0025 This attribute defines the name of the person who has
signing authority for service."
    ::= { cooTableEntry 25 }
cooOutsourcingProviderFeeName                   OBJECT-TYPE
    SYNTAX      DellCostofOwnershipString
    ACCESS      read-write
    STATUS      mandatory
    DESCRIPTION
"1600.0010.0001.0026 This attribute defines any additional outsourcing
charge for service."
    ::= { cooTableEntry 26 }
cooOutsourcingProviderServiceLevelName          OBJECT-TYPE
    SYNTAX      DellCostofOwnershipString
    ACCESS      read-write
    STATUS      mandatory
    DESCRIPTION
"1600.0010.0001.0027 This attribute defines the service level agreement
for service."
    ::= { cooTableEntry 27 }
cooInsuranceCompanyName                         OBJECT-TYPE
    SYNTAX      DellCostofOwnershipString
    ACCESS      read-write
    STATUS      mandatory
    DESCRIPTION
"1600.0010.0001.0028 This attribute defines the name of the company
insuring the system."
    ::= { cooTableEntry 28 }
cooBoxAssetTagName                              OBJECT-TYPE
    SYNTAX      DellCostofOwnershipString
    ACCESS      read-write
    STATUS      mandatory
    DESCRIPTION
"1600.0010.0001.0029 This attribute defines the name the system asset tag."
    ::= { cooTableEntry 29 }
cooBoxSystemName                                OBJECT-TYPE
    SYNTAX      DellCostofOwnershipString
    ACCESS      read-write
    STATUS      mandatory
    DESCRIPTION
"1600.0010.0001.0030 This attribute defines the name of the system."
    ::= { cooTableEntry 30 }
cooBoxCPUSerialNumberName                       OBJECT-TYPE
    SYNTAX      DellCostofOwnershipString
    ACCESS      read-write
    STATUS      mandatory
    DESCRIPTION
"1600.0010.0001.0031 This attribute defines the name of the CPU serial
number in the system."
    ::= { cooTableEntry 31 }
cooOperatingSystemUpgradeTypeName               OBJECT-TYPE
    SYNTAX      DellCostofOwnershipString
    ACCESS      read-write
    STATUS      mandatory
    DESCRIPTION
"1600.0010.0001.0032 This attribute defines the name the operating system
on the system."
    ::= { cooTableEntry 32 }
cooOperatingSystemUpgradePatchLevelName         OBJECT-TYPE
    SYNTAX      DellCostofOwnershipString
    ACCESS      read-write
    STATUS      mandatory
    DESCRIPTION
"1600.0010.0001.0033 This attribute defines the operating system patch level
of the system."
    ::= { cooTableEntry 33 }
cooOperatingSystemUpgradeDate                   OBJECT-TYPE
    SYNTAX      DellCostofOwnershipString
    ACCESS      read-write
    STATUS      mandatory
    DESCRIPTION
"1600.0010.0001.0034 This attribute defines the operating system upgrade date
of the system."
    ::= { cooTableEntry 34 }
cooDepreciationDuration                         OBJECT-TYPE
    SYNTAX      DellUnsigned32BitRange
    ACCESS      read-write
    STATUS      mandatory
    DESCRIPTION
"1600.0010.0001.0035 This attribute defines the depreciation duration time
for the system."
    ::= { cooTableEntry 35 }
cooDepreciationDurationType                     OBJECT-TYPE
    SYNTAX      DellCooMonthYearDurationType
    ACCESS      read-write
    STATUS      mandatory
    DESCRIPTION
"1600.0010.0001.0036 This attribute defines the depreciation duration time
unit for the system."
    ::= { cooTableEntry 36 }
cooDepreciationPercentage                       OBJECT-TYPE
    SYNTAX      DellUnsigned32BitRange
    ACCESS      read-write
    STATUS      mandatory
    DESCRIPTION
"1600.0010.0001.0037 This attribute defines the percentage of depreciation
for the system."
    ::= { cooTableEntry 37 }
cooDepreciationMethodName                       OBJECT-TYPE
    SYNTAX      DellCostofOwnershipString
    ACCESS      read-write
    STATUS      mandatory
    DESCRIPTION
"1600.0010.0001.0038 This attribute defines the method of Depreciation
for the system."
    ::= { cooTableEntry 38 }
cooRegistrationIsRegistered                     OBJECT-TYPE
    SYNTAX      DellBoolean
    ACCESS      read-write
    STATUS      mandatory
    DESCRIPTION
"1600.0010.0001.0039 This attribute defines if the system is registered
or not."
    ::= { cooTableEntry 39 }


-------------------------------------------------------------------------------
-- Cost Of Ownership (COO) Service Contract Table
--
-- OID Format: 1.3.6.1.4.1.674.10892.1.1600.20.1.<a>.<i1>.<i2>
-------------------------------------------------------------------------------

CooServiceContractTableEntry                    ::= SEQUENCE {
    cooServiceContractchassisIndex              DellObjectRange,
    cooServiceContractIndex                     DellObjectRange,
    cooServiceContractState                     DellStateSettings,
    cooServiceContractWasRenewed                DellBoolean,
    cooServiceContractTypeName                  DellCostofOwnershipString,
    cooServiceContractVendorName                DellCostofOwnershipString
}

cooServiceContractTable                         OBJECT-TYPE
    SYNTAX      SEQUENCE OF CooServiceContractTableEntry
    ACCESS      not-accessible
    STATUS      mandatory
    DESCRIPTION
"1600.0020 This object defines the Cost Of Ownership (COO) Service Contract
Table."
    ::= { cooGroup 20 }
cooServiceContractTableEntry                    OBJECT-TYPE
    SYNTAX      CooServiceContractTableEntry
    ACCESS      not-accessible
    STATUS      mandatory
    DESCRIPTION
"1600.0020.0001 This object defines the Cost Of Ownership (COO) Service
Contract Table Entry."
    INDEX       { cooServiceContractchassisIndex,
                  cooServiceContractIndex }
    ::= { cooServiceContractTable 1 }

cooServiceContractchassisIndex                  OBJECT-TYPE
    SYNTAX      DellObjectRange
    ACCESS      read-only
    STATUS      mandatory
    DESCRIPTION
"1600.0020.0001.0001 This attribute defines the index (one based) of the
associated chassis."
    ::= { cooServiceContractTableEntry 1 }
cooServiceContractIndex                         OBJECT-TYPE
    SYNTAX      DellObjectRange
    ACCESS      read-only
    STATUS      mandatory
    DESCRIPTION
"1600.0020.0001.0002 This attribute defines the index (one based) of the
COO service contract."
    ::= { cooServiceContractTableEntry 2 }
cooServiceContractState                         OBJECT-TYPE
    SYNTAX      DellStateSettings
    ACCESS      read-only
    STATUS      mandatory
    DESCRIPTION
"1600.0020.0001.0003 This attribute defines the state settings of the
COO service contract."
    ::= { cooServiceContractTableEntry 3 }
cooServiceContractWasRenewed                    OBJECT-TYPE
    SYNTAX      DellBoolean
    ACCESS      read-write
    STATUS      mandatory
    DESCRIPTION
"1600.0020.0001.0004 This attribute defines if the COO service contract
was renewed not."
    ::= { cooServiceContractTableEntry 4 }
cooServiceContractTypeName                      OBJECT-TYPE
    SYNTAX      DellCostofOwnershipString
    ACCESS      read-write
    STATUS      mandatory
    DESCRIPTION
"1600.0020.0001.0005 This attribute defines the name of the type of
COO service contract."
    ::= { cooServiceContractTableEntry 5 }
cooServiceContractVendorName                    OBJECT-TYPE
    SYNTAX      DellCostofOwnershipString
    ACCESS      read-write
    STATUS      mandatory
    DESCRIPTION
"1600.0020.0001.0006 This attribute defines the name of the provider of the
COO service contract."
    ::= { cooServiceContractTableEntry 6 }


-------------------------------------------------------------------------------
-- Cost Of Ownership (COO) Cost Event Log Table
--
-- OID Format: 1.3.6.1.4.1.674.10892.1.1600.30.1.<a>.<i1>.<i2>
-------------------------------------------------------------------------------

CooCostEventLogTableEntry                       ::= SEQUENCE {
    cooCostEventLogchassisIndex                 DellObjectRange,
    cooCostEventLogIndex                        DellObjectRange,
    cooCostEventLogState                        DellStateSettings,
    cooCostEventLogDuration                     DellUnsigned32BitRange,
    cooCostEventLogDurationType                 DellCooHourDayDurationType,
    cooCostEventLogDescriptionName              DellCostofOwnershipString
}

cooCostEventLogTable                            OBJECT-TYPE
    SYNTAX      SEQUENCE OF CooCostEventLogTableEntry
    ACCESS      not-accessible
    STATUS      mandatory
    DESCRIPTION
"1600.0030 This object defines the Cost Of Ownership (COO) Cost Event Log
Table."
    ::= { cooGroup 30 }
cooCostEventLogTableEntry                       OBJECT-TYPE
    SYNTAX      CooCostEventLogTableEntry
    ACCESS      not-accessible
    STATUS      mandatory
    DESCRIPTION
"1600.0030.0001 This object defines the Cost Of Ownership (COO) Cost Event
Log Table Entry."
    INDEX       { cooCostEventLogchassisIndex,
                  cooCostEventLogIndex }
    ::= { cooCostEventLogTable 1 }

cooCostEventLogchassisIndex                     OBJECT-TYPE
    SYNTAX      DellObjectRange
    ACCESS      read-only
    STATUS      mandatory
    DESCRIPTION
"1600.0030.0001.0001 This attribute defines the index (one based) of the
associated chassis."
    ::= { cooCostEventLogTableEntry 1 }
cooCostEventLogIndex                            OBJECT-TYPE
    SYNTAX      DellObjectRange
    ACCESS      read-only
    STATUS      mandatory
    DESCRIPTION
"1600.0030.0001.0002 This attribute defines the index (one based) of the
COO cost event log entry."
    ::= { cooCostEventLogTableEntry 2 }
cooCostEventLogState                            OBJECT-TYPE
    SYNTAX      DellStateSettings
    ACCESS      read-only
    STATUS      mandatory
    DESCRIPTION
"1600.0030.0001.0003 This attribute defines the state settings of the
COO cost event log entry."
    ::= { cooCostEventLogTableEntry 3 }
cooCostEventLogDuration                         OBJECT-TYPE
    SYNTAX      DellUnsigned32BitRange
    ACCESS      read-write
    STATUS      mandatory
    DESCRIPTION
"1600.0030.0001.0004 This attribute defines the duration of the
COO cost event."
    ::= { cooCostEventLogTableEntry 4 }
cooCostEventLogDurationType                     OBJECT-TYPE
    SYNTAX      DellCooHourDayDurationType
    ACCESS      read-write
    STATUS      mandatory
    DESCRIPTION
"1600.0030.0001.0005 This attribute defines the duration type of the
COO cost event."
    ::= { cooCostEventLogTableEntry 5 }
cooCostEventLogDescriptionName                  OBJECT-TYPE
    SYNTAX      DellCostofOwnershipString
    ACCESS      read-write
    STATUS      mandatory
    DESCRIPTION
"1600.0030.0001.0006 This attribute defines the description of the
COO cost event."
    ::= { cooCostEventLogTableEntry 6 }


-------------------------------------------------------------------------------
-- Cost Of Ownership (COO) Warranty Table
--
-- OID Format: 1.3.6.1.4.1.674.10892.1.1600.40.1.<a>.<i1>.<i2>
-------------------------------------------------------------------------------

CooWarrantyTableEntry                           ::= SEQUENCE {
    cooWarrantychassisIndex                     DellObjectRange,
    cooWarrantyIndex                            DellObjectRange,
    cooWarrantyState                            DellStateSettings,
    cooWarrantyDuration                         DellUnsigned32BitRange,
    cooWarrantyDurationType                     DellCooDayMonthDurationType,
    cooWarrantyEndDateName                      DellDateName,
    cooWarrantyCost                             DellUnsigned32BitRange
}

cooWarrantyTable                                OBJECT-TYPE
    SYNTAX      SEQUENCE OF CooWarrantyTableEntry
    ACCESS      not-accessible
    STATUS      mandatory
    DESCRIPTION
"1600.0040 This object defines the Cost Of Ownership (COO) Warranty Table."
    ::= { cooGroup 40 }
cooWarrantyTableEntry                           OBJECT-TYPE
    SYNTAX      CooWarrantyTableEntry
    ACCESS      not-accessible
    STATUS      mandatory
    DESCRIPTION
"1600.0040.0001 This object defines the Cost Of Ownership (COO) Warranty
Table Entry."
    INDEX       { cooWarrantychassisIndex,
                  cooWarrantyIndex }
    ::= { cooWarrantyTable 1 }

cooWarrantychassisIndex                         OBJECT-TYPE
    SYNTAX      DellObjectRange
    ACCESS      read-only
    STATUS      mandatory
    DESCRIPTION
"1600.0040.0001.0001 This attribute defines the index (one based) of the
associated chassis."
    ::= { cooWarrantyTableEntry 1 }
cooWarrantyIndex                                OBJECT-TYPE
    SYNTAX      DellObjectRange
    ACCESS      read-only
    STATUS      mandatory
    DESCRIPTION
"1600.0040.0001.0002 This attribute defines the index (one based) of the
COO warranty."
    ::= { cooWarrantyTableEntry 2 }
cooWarrantyState                                OBJECT-TYPE
    SYNTAX      DellStateSettings
    ACCESS      read-only
    STATUS      mandatory
    DESCRIPTION
"1600.0040.0001.0003 This attribute defines the state settings of the
COO warranty."
    ::= { cooWarrantyTableEntry 3 }
cooWarrantyDuration                             OBJECT-TYPE
    SYNTAX      DellUnsigned32BitRange
    ACCESS      read-write
    STATUS      mandatory
    DESCRIPTION
"1600.0040.0001.0004 This attribute defines the duration of the COO warranty."
    ::= { cooWarrantyTableEntry 4 }
cooWarrantyDurationType                         OBJECT-TYPE
    SYNTAX      DellCooDayMonthDurationType
    ACCESS      read-write
    STATUS      mandatory
    DESCRIPTION
"1600.0040.0001.0005 This attribute defines the duration type of the
COO warranty."
    ::= { cooWarrantyTableEntry 5 }
cooWarrantyEndDateName                          OBJECT-TYPE
    SYNTAX      DellDateName
    ACCESS      read-write
    STATUS      mandatory
    DESCRIPTION
"1600.0040.0001.0006 This attribute defines the end date of the COO warranty.
Dates are defined in the ASCII format:
    yyyyMMddhhmmss.uuuuuu+fff or yyyyMMddhhmmss.uuuuuu-fff
where yyyy is the year, MM is the month, dd is the day, hh are the hours,
mm are the minutes, ss are the seconds, uuuuuu are the microseconds and
+fff or -fff is the offset from UTC in minutes."
    ::= { cooWarrantyTableEntry 6 }
cooWarrantyCost                                 OBJECT-TYPE
    SYNTAX      DellUnsigned32BitRange
    ACCESS      read-write
    STATUS      mandatory
    DESCRIPTION
"1600.0040.0001.0007 This attribute defines the cost of the COO warranty."
    ::= { cooWarrantyTableEntry 7 }


-------------------------------------------------------------------------------
-- Cost Of Ownership (COO) Lease Information Table
--
-- OID Format: 1.3.6.1.4.1.674.10892.1.1600.50.1.<a>.<i1>.<i2>
-------------------------------------------------------------------------------

CooLeaseInformationTableEntry                   ::= SEQUENCE {
    cooLeaseInformationchassisIndex             DellObjectRange,
    cooLeaseInformationIndex                    DellObjectRange,
    cooLeaseInformationState                    DellStateSettings,
    cooLeaseInformationMultipleSchedules        DellBoolean,
    cooLeaseInformationBuyOutAmount             DellUnsigned32BitRange,
    cooLeaseInformationLeaseRateFactor          DellUnsigned32BitRange,
    cooLeaseInformationEndDateName              DellDateName,
    cooLeaseInformationFairMarketValue          DellUnsigned32BitRange,
    cooLeaseInformationLessorName               DellCostofOwnershipString
}

cooLeaseInformationTable                        OBJECT-TYPE
    SYNTAX      SEQUENCE OF CooLeaseInformationTableEntry
    ACCESS      not-accessible
    STATUS      mandatory
    DESCRIPTION
"1600.0050 This object defines the Cost Of Ownership (COO) Lease Information
Table."
    ::= { cooGroup 50 }
cooLeaseInformationTableEntry                   OBJECT-TYPE
    SYNTAX      CooLeaseInformationTableEntry
    ACCESS      not-accessible
    STATUS      mandatory
    DESCRIPTION
"1600.0050.0001 This object defines the Cost Of Ownership (COO) Lease
Information Table Entry."
    INDEX       { cooLeaseInformationchassisIndex,
                  cooLeaseInformationIndex }
    ::= { cooLeaseInformationTable 1 }

cooLeaseInformationchassisIndex                 OBJECT-TYPE
    SYNTAX      DellObjectRange
    ACCESS      read-only
    STATUS      mandatory
    DESCRIPTION
"1600.0050.0001.0001 This attribute defines the index (one based) of the
associated chassis."
    ::= { cooLeaseInformationTableEntry 1 }
cooLeaseInformationIndex                        OBJECT-TYPE
    SYNTAX      DellObjectRange
    ACCESS      read-only
    STATUS      mandatory
    DESCRIPTION
"1600.0050.0001.0002 This attribute defines the index (one based) of the
COO lease information."
    ::= { cooLeaseInformationTableEntry 2 }
cooLeaseInformationState                        OBJECT-TYPE
    SYNTAX      DellStateSettings
    ACCESS      read-only
    STATUS      mandatory
    DESCRIPTION
"1600.0050.0001.0003 This attribute defines the state settings of the
COO lease information."
    ::= { cooLeaseInformationTableEntry 3 }
cooLeaseInformationMultipleSchedules            OBJECT-TYPE
    SYNTAX      DellBoolean
    ACCESS      read-only
    STATUS      mandatory
    DESCRIPTION
"1600.0050.0001.0004 This attribute defines if there are multiple schedules
for this lease."
    ::= { cooLeaseInformationTableEntry 4 }
cooLeaseInformationBuyOutAmount                 OBJECT-TYPE
    SYNTAX      DellUnsigned32BitRange
    ACCESS      read-write
    STATUS      mandatory
    DESCRIPTION
"1600.0050.0001.0005 This attribute defines buy out amount for this lease."
    ::= { cooLeaseInformationTableEntry 5 }
cooLeaseInformationLeaseRateFactor              OBJECT-TYPE
    SYNTAX      DellUnsigned32BitRange
    ACCESS      read-write
    STATUS      mandatory
    DESCRIPTION
"1600.0050.0001.0006 This attribute defines the rate factor for this lease."
    ::= { cooLeaseInformationTableEntry 6 }
cooLeaseInformationEndDateName                  OBJECT-TYPE
    SYNTAX      DellDateName
    ACCESS      read-write
    STATUS      mandatory
    DESCRIPTION
"1600.0050.0001.0007 This attribute defines the end date for this lease.
Dates are defined in the ASCII format:
    yyyyMMddhhmmss.uuuuuu+fff or yyyyMMddhhmmss.uuuuuu-fff
where yyyy is the year, MM is the month, dd is the day, hh are the hours,
mm are the minutes, ss are the seconds, uuuuuu are the microseconds and
+fff or -fff is the offset from UTC in minutes."
    ::= { cooLeaseInformationTableEntry 7 }
cooLeaseInformationFairMarketValue              OBJECT-TYPE
    SYNTAX      DellUnsigned32BitRange
    ACCESS      read-write
    STATUS      mandatory
    DESCRIPTION
"1600.0050.0001.0008 This attribute defines the fair market value
for this lease."
    ::= { cooLeaseInformationTableEntry 8 }
cooLeaseInformationLessorName                   OBJECT-TYPE
    SYNTAX      DellCostofOwnershipString
    ACCESS      read-write
    STATUS      mandatory
    DESCRIPTION
"1600.0050.0001.0009 This attribute defines the name of the lessor
for this lease."
    ::= { cooLeaseInformationTableEntry 9 }


-------------------------------------------------------------------------------
-- Cost Of Ownership (COO) Schedule Number Table
--
-- OID Format: 1.3.6.1.4.1.674.10892.1.1600.60.1.<a>.<i1>.<i2>
-------------------------------------------------------------------------------

CooScheduleNumberTableEntry                     ::= SEQUENCE {
    cooScheduleNumberchassisIndex               DellObjectRange,
    cooScheduleNumberIndex                      DellObjectRange,
    cooScheduleNumberState                      DellStateSettings,
    cooScheduleNumberLeaseInformationIndexReference  DellUnsigned32BitRange,
    cooScheduleNumberDescriptionName            DellCostofOwnershipString
}

cooScheduleNumberTable                          OBJECT-TYPE
    SYNTAX      SEQUENCE OF CooScheduleNumberTableEntry
    ACCESS      not-accessible
    STATUS      mandatory
    DESCRIPTION
"1600.0060 This object defines the Cost Of Ownership (COO) Schedule Number
Table."
    ::= { cooGroup 60 }
cooScheduleNumberTableEntry                     OBJECT-TYPE
    SYNTAX      CooScheduleNumberTableEntry
    ACCESS      not-accessible
    STATUS      mandatory
    DESCRIPTION
"1600.0060.0001 This object defines the Cost Of Ownership (COO) Schedule Number
Table Entry."
    INDEX       { cooScheduleNumberchassisIndex,
                  cooScheduleNumberIndex }
    ::= { cooScheduleNumberTable 1 }

cooScheduleNumberchassisIndex                   OBJECT-TYPE
    SYNTAX      DellObjectRange
    ACCESS      read-only
    STATUS      mandatory
    DESCRIPTION
"1600.0060.0001.0001 This attribute defines the index (one based) of the
associated chassis."
    ::= { cooScheduleNumberTableEntry 1 }
cooScheduleNumberIndex                          OBJECT-TYPE
    SYNTAX      DellObjectRange
    ACCESS      read-only
    STATUS      mandatory
    DESCRIPTION
"1600.0060.0001.0002 This attribute defines the index (one based) of the
COO schedule number."
    ::= { cooScheduleNumberTableEntry 2 }
cooScheduleNumberState                          OBJECT-TYPE
    SYNTAX      DellStateSettings
    ACCESS      read-only
    STATUS      mandatory
    DESCRIPTION
"1600.0060.0001.0003 This attribute defines the state settings of the
COO schedule number."
    ::= { cooScheduleNumberTableEntry 3 }
cooScheduleNumberLeaseInformationIndexReference OBJECT-TYPE
    SYNTAX      DellUnsigned32BitRange
    ACCESS      read-write
    STATUS      mandatory
    DESCRIPTION
"1600.0060.0001.0004 This attribute defines the index (one based) of the
COO lease information associated with the COO schedule number."
    ::= { cooScheduleNumberTableEntry 4 }
cooScheduleNumberDescriptionName                OBJECT-TYPE
    SYNTAX      DellCostofOwnershipString
    ACCESS      read-write
    STATUS      mandatory
    DESCRIPTION
"1600.0060.0001.0005 This attribute defines the description of the
COO schedule number."
    ::= { cooScheduleNumberTableEntry 5 }


-------------------------------------------------------------------------------
-- Cost Of Ownership (COO) Options Table
--
-- OID Format: 1.3.6.1.4.1.674.10892.1.1600.70.1.<a>.<i1>.<i2>
-------------------------------------------------------------------------------

CooOptionsTableEntry                            ::= SEQUENCE {
    cooOptionschassisIndex                      DellObjectRange,
    cooOptionsIndex                             DellObjectRange,
    cooOptionsState                             DellStateSettings,
    cooOptionsLeaseInformationIndexReference    DellUnsigned32BitRange,
    cooOptionsDescriptionName                   DellCostofOwnershipString
}

cooOptionsTable                                 OBJECT-TYPE
    SYNTAX      SEQUENCE OF CooOptionsTableEntry
    ACCESS      not-accessible
    STATUS      mandatory
    DESCRIPTION
"1600.0070 This object defines the Cost Of Ownership (COO) Options Table."
    ::= { cooGroup 70 }
cooOptionsTableEntry                            OBJECT-TYPE
    SYNTAX      CooOptionsTableEntry
    ACCESS      not-accessible
    STATUS      mandatory
    DESCRIPTION
"1600.0070.0001 This object defines the Cost Of Ownership (COO) Options Table
Entry."
    INDEX       { cooOptionschassisIndex,
                  cooOptionsIndex }
    ::= { cooOptionsTable 1 }

cooOptionschassisIndex                          OBJECT-TYPE
    SYNTAX      DellObjectRange
    ACCESS      read-only
    STATUS      mandatory
    DESCRIPTION
"1600.0070.0001.0001 This attribute defines the index (one based) of the
associated chassis."
    ::= { cooOptionsTableEntry 1 }
cooOptionsIndex                                 OBJECT-TYPE
    SYNTAX      DellObjectRange
    ACCESS      read-only
    STATUS      mandatory
    DESCRIPTION
"1600.0070.0001.0002 This attribute defines the index (one based) of the
COO options."
    ::= { cooOptionsTableEntry 2 }
cooOptionsState                                 OBJECT-TYPE
    SYNTAX      DellStateSettings
    ACCESS      read-only
    STATUS      mandatory
    DESCRIPTION
"1600.0070.0001.0003 This attribute defines the state settings of the
COO options."
    ::= { cooOptionsTableEntry 3 }
cooOptionsLeaseInformationIndexReference        OBJECT-TYPE
    SYNTAX      DellUnsigned32BitRange
    ACCESS      read-write
    STATUS      mandatory
    DESCRIPTION
"1600.0070.0001.0004 This attribute defines the index (one based) of the
COO lease information associated with the COO options."
    ::= { cooOptionsTableEntry 4 }
cooOptionsDescriptionName                       OBJECT-TYPE
    SYNTAX      DellCostofOwnershipString
    ACCESS      read-write
    STATUS      mandatory
    DESCRIPTION
"1600.0070.0001.0005 This attribute defines the description of the
COO options."
    ::= { cooOptionsTableEntry 5 }


-------------------------------------------------------------------------------
-- Cost Of Ownership (COO) Maintenance Table
--
-- OID Format: 1.3.6.1.4.1.674.10892.1.1600.80.1.<a>.<i1>.<i2>
-------------------------------------------------------------------------------

CooMaintenanceTableEntry                        ::= SEQUENCE {
    cooMaintenancechassisIndex                  DellObjectRange,
    cooMaintenanceIndex                         DellObjectRange,
    cooMaintenanceState                         DellStateSettings,
    cooMaintenanceStartDateName                 DellDateName,
    cooMaintenanceEndDateName                   DellDateName,
    cooMaintenanceProviderName                  DellCostofOwnershipString,
    cooMaintenanceRestrictionsName              DellCostofOwnershipString
}

cooMaintenanceTable                             OBJECT-TYPE
    SYNTAX      SEQUENCE OF CooMaintenanceTableEntry
    ACCESS      not-accessible
    STATUS      mandatory
    DESCRIPTION
"1600.0080 This object defines the Cost Of Ownership (COO) Maintenance Table."
    ::= { cooGroup 80 }
cooMaintenanceTableEntry                        OBJECT-TYPE
    SYNTAX      CooMaintenanceTableEntry
    ACCESS      not-accessible
    STATUS      mandatory
    DESCRIPTION
"1600.0080.0001 This object defines the Cost Of Ownership (COO) Maintenance
Table Entry."
    INDEX       { cooMaintenancechassisIndex,
                  cooMaintenanceIndex }
    ::= { cooMaintenanceTable 1 }

cooMaintenancechassisIndex                      OBJECT-TYPE
    SYNTAX      DellObjectRange
    ACCESS      read-only
    STATUS      mandatory
    DESCRIPTION
"1600.0080.0001.0001 This attribute defines the index (one based) of the
associated chassis."
    ::= { cooMaintenanceTableEntry 1 }
cooMaintenanceIndex                             OBJECT-TYPE
    SYNTAX      DellObjectRange
    ACCESS      read-only
    STATUS      mandatory
    DESCRIPTION
"1600.0080.0001.0002 This attribute defines the index (one based) of the
COO maintenance."
    ::= { cooMaintenanceTableEntry 2 }
cooMaintenanceState                             OBJECT-TYPE
    SYNTAX      DellStateSettings
    ACCESS      read-only
    STATUS      mandatory
    DESCRIPTION
"1600.0080.0001.0003 This attribute defines the state settings of the
COO maintenance."
    ::= { cooMaintenanceTableEntry 3 }
cooMaintenanceStartDateName                     OBJECT-TYPE
    SYNTAX      DellDateName
    ACCESS      read-write
    STATUS      mandatory
    DESCRIPTION
"1600.0080.0001.0004 This attribute defines the start date of the
COO maintenance.  Dates are defined in the ASCII format:
    yyyyMMddhhmmss.uuuuuu+fff or yyyyMMddhhmmss.uuuuuu-fff
where yyyy is the year, MM is the month, dd is the day, hh are the hours,
mm are the minutes, ss are the seconds, uuuuuu are the microseconds and
+fff or -fff is the offset from UTC in minutes."
    ::= { cooMaintenanceTableEntry 4 }
cooMaintenanceEndDateName                       OBJECT-TYPE
    SYNTAX      DellDateName
    ACCESS      read-write
    STATUS      mandatory
    DESCRIPTION
"1600.0080.0001.0005 This attribute defines the end date of the
COO maintenance.  Dates are defined in the ASCII format:
    yyyyMMddhhmmss.uuuuuu+fff or yyyyMMddhhmmss.uuuuuu-fff
where yyyy is the year, MM is the month, dd is the day, hh are the hours,
mm are the minutes, ss are the seconds, uuuuuu are the microseconds and
+fff or -fff is the offset from UTC in minutes."
    ::= { cooMaintenanceTableEntry 5 }
cooMaintenanceProviderName                      OBJECT-TYPE
    SYNTAX      DellCostofOwnershipString
    ACCESS      read-write
    STATUS      mandatory
    DESCRIPTION
"1600.0080.0001.0006 This attribute defines the name of the provider of the
COO maintenance."
    ::= { cooMaintenanceTableEntry 6 }
cooMaintenanceRestrictionsName                  OBJECT-TYPE
    SYNTAX      DellCostofOwnershipString
    ACCESS      read-write
    STATUS      mandatory
    DESCRIPTION
"1600.0080.0001.0007 This attribute defines the text of the maintenance
agreement restrictions."
    ::= { cooMaintenanceTableEntry 7 }


-------------------------------------------------------------------------------
-- Cost Of Ownership (COO) Repair Table
--
-- OID Format: 1.3.6.1.4.1.674.10892.1.1600.90.1.<a>.<i1>.<i2>
-------------------------------------------------------------------------------

CooRepairTableEntry                             ::= SEQUENCE {
    cooRepairchassisIndex                       DellObjectRange,
    cooRepairIndex                              DellObjectRange,
    cooRepairState                              DellStateSettings,
    cooRepairCounter                            DellUnsigned32BitRange,
    cooRepairVendorName                         DellCostofOwnershipString
}

cooRepairTable                                  OBJECT-TYPE
    SYNTAX      SEQUENCE OF CooRepairTableEntry
    ACCESS      not-accessible
    STATUS      mandatory
    DESCRIPTION
"1600.0090 This object defines the Cost Of Ownership (COO) Repair Table."
    ::= { cooGroup 90 }
cooRepairTableEntry                             OBJECT-TYPE
    SYNTAX      CooRepairTableEntry
    ACCESS      not-accessible
    STATUS      mandatory
    DESCRIPTION
"1600.0090.0001 This object defines the Cost Of Ownership (COO) Repair Table
Entry."
    INDEX       { cooRepairchassisIndex,
                  cooRepairIndex }
    ::= { cooRepairTable 1 }

cooRepairchassisIndex                           OBJECT-TYPE
    SYNTAX      DellObjectRange
    ACCESS      read-only
    STATUS      mandatory
    DESCRIPTION
"1600.0090.0001.0001 This attribute defines the index (one based) of the
associated chassis."
    ::= { cooRepairTableEntry 1 }
cooRepairIndex                                  OBJECT-TYPE
    SYNTAX      DellObjectRange
    ACCESS      read-only
    STATUS      mandatory
    DESCRIPTION
"1600.0090.0001.0002 This attribute defines the index (one based) of the
COO repair."
    ::= { cooRepairTableEntry 2 }
cooRepairState                                  OBJECT-TYPE
    SYNTAX      DellStateSettings
    ACCESS      read-only
    STATUS      mandatory
    DESCRIPTION
"1600.0090.0001.0003 This attribute defines the state setting of the
COO repair."
    ::= { cooRepairTableEntry 3 }
cooRepairCounter                                OBJECT-TYPE
    SYNTAX      DellUnsigned32BitRange
    ACCESS      read-write
    STATUS      mandatory
    DESCRIPTION
"1600.0090.0001.0004 This attribute defines the number of repairs this
system has had."
    ::= { cooRepairTableEntry 4 }
cooRepairVendorName                             OBJECT-TYPE
    SYNTAX      DellCostofOwnershipString
    ACCESS      read-write
    STATUS      mandatory
    DESCRIPTION
"1600.0090.0001.0005 This attribute defines the repair vendors's name."
    ::= { cooRepairTableEntry 5 }


-------------------------------------------------------------------------------
-- Cost Of Ownership (COO) Support Information Table
--
-- OID Format: 1.3.6.1.4.1.674.10892.1.1600.100.1.<a>.<i1>.<i2>
-------------------------------------------------------------------------------

CooSupportInformationTableEntry                 ::= SEQUENCE {
    cooSupportInformationchassisIndex           DellObjectRange,
    cooSupportInformationIndex                  DellObjectRange,
    cooSupportInformationState                  DellStateSettings,
    cooSupportInformationIsOutsourced           DellBoolean,
    cooSupportInformationType                   DellUnsigned32BitRange,
    cooSupportInformationHelpDeskName           DellCostofOwnershipString,
    cooSupportInformationFixTypeName            DellCostofOwnershipString
}

cooSupportInformationTable                      OBJECT-TYPE
    SYNTAX      SEQUENCE OF CooSupportInformationTableEntry
    ACCESS      not-accessible
    STATUS      mandatory
    DESCRIPTION
"1600.0100 This object defines the Cost Of Ownership (COO) Support
Information Table."
    ::= { cooGroup 100 }
cooSupportInformationTableEntry                 OBJECT-TYPE
    SYNTAX      CooSupportInformationTableEntry
    ACCESS      not-accessible
    STATUS      mandatory
    DESCRIPTION
"1600.0100.0001 This object defines the Cost Of Ownership (COO) Support
Information Table Entry."
    INDEX       { cooSupportInformationchassisIndex,
                  cooSupportInformationIndex }
    ::= { cooSupportInformationTable 1 }

cooSupportInformationchassisIndex               OBJECT-TYPE
    SYNTAX      DellObjectRange
    ACCESS      read-only
    STATUS      mandatory
    DESCRIPTION
"1600.0100.0001.0001 This attribute defines the index (one based) of the
associated chassis."
    ::= { cooSupportInformationTableEntry 1 }
cooSupportInformationIndex                      OBJECT-TYPE
    SYNTAX      DellObjectRange
    ACCESS      read-only
    STATUS      mandatory
    DESCRIPTION
"1600.0100.0001.0002 This attribute defines the index (one based) of the
COO support information."
    ::= { cooSupportInformationTableEntry 2 }
cooSupportInformationState                      OBJECT-TYPE
    SYNTAX      DellStateSettings
    ACCESS      read-only
    STATUS      mandatory
    DESCRIPTION
"1600.0100.0001.0003 This attribute defines the state setting of the
COO support information."
    ::= { cooSupportInformationTableEntry 3 }
cooSupportInformationIsOutsourced               OBJECT-TYPE
    SYNTAX      DellBoolean
    ACCESS      read-write
    STATUS      mandatory
    DESCRIPTION
"1600.0100.0001.0004 This attribute defines if support is outsourced or not."
    ::= { cooSupportInformationTableEntry 4 }
cooSupportInformationType                       OBJECT-TYPE
    SYNTAX      DellUnsigned32BitRange
    ACCESS      read-write
    STATUS      mandatory
    DESCRIPTION
"1600.0100.0001.0005 This attribute defines the type of the conmponent,
system or network problem that occurred."
    ::= { cooSupportInformationTableEntry 5 }
cooSupportInformationHelpDeskName               OBJECT-TYPE
    SYNTAX      DellCostofOwnershipString
    ACCESS      read-write
    STATUS      mandatory
    DESCRIPTION
"1600.0100.0001.0006 This attribute defines the help desk support
information provided."
    ::= { cooSupportInformationTableEntry 6 }
cooSupportInformationFixTypeName                OBJECT-TYPE
    SYNTAX      DellCostofOwnershipString
    ACCESS      read-write
    STATUS      mandatory
    DESCRIPTION
"1600.0100.0001.0007 This attribute defines the method used to fix
the problem."
    ::= { cooSupportInformationTableEntry 7 }


-------------------------------------------------------------------------------
-- Cost Of Ownership (COO) Trouble Ticket Table
--
-- OID Format: 1.3.6.1.4.1.674.10892.1.1600.110.1.<a>.<i1>.<i2>
-------------------------------------------------------------------------------

CooTroubleTicketTableEntry                      ::= SEQUENCE {
    cooTroubleTicketchassisIndex                DellObjectRange,
    cooTroubleTicketIndex                       DellObjectRange,
    cooTroubleTicketState                       DellStateSettings,
    cooTroubleTicketSupportInformationIndexReference  DellUnsigned32BitRange,
    cooTroubleTicketNumberName                  DellCostofOwnershipString
}

cooTroubleTicketTable                           OBJECT-TYPE
    SYNTAX      SEQUENCE OF CooTroubleTicketTableEntry
    ACCESS      not-accessible
    STATUS      mandatory
    DESCRIPTION
"1600.0110 This object defines the Cost Of Ownership (COO) Trouble Ticket
Table."
    ::= { cooGroup 110 }
cooTroubleTicketTableEntry                      OBJECT-TYPE
    SYNTAX      CooTroubleTicketTableEntry
    ACCESS      not-accessible
    STATUS      mandatory
    DESCRIPTION
"1600.0110.0001 This object defines the Cost Of Ownership (COO) Trouble Ticket
Table Entry."
    INDEX       { cooTroubleTicketchassisIndex,
                  cooTroubleTicketIndex }
    ::= { cooTroubleTicketTable 1 }

cooTroubleTicketchassisIndex                    OBJECT-TYPE
    SYNTAX      DellObjectRange
    ACCESS      read-only
    STATUS      mandatory
    DESCRIPTION
"1600.0110.0001.0001 This attribute defines the index (one based) of the
associated chassis."
    ::= { cooTroubleTicketTableEntry 1 }
cooTroubleTicketIndex                           OBJECT-TYPE
    SYNTAX      DellObjectRange
    ACCESS      read-only
    STATUS      mandatory
    DESCRIPTION
"1600.0110.0001.0002 This attribute defines the index (one based) of the
COO trouble ticket."
    ::= { cooTroubleTicketTableEntry 2 }
cooTroubleTicketState                           OBJECT-TYPE
    SYNTAX      DellStateSettings
    ACCESS      read-only
    STATUS      mandatory
    DESCRIPTION
"1600.0110.0001.0003 This attribute defines the state settings of the
COO trouble ticket."
    ::= { cooTroubleTicketTableEntry 3 }
cooTroubleTicketSupportInformationIndexReference OBJECT-TYPE
    SYNTAX      DellUnsigned32BitRange
    ACCESS      read-write
    STATUS      mandatory
    DESCRIPTION
"1600.0110.0001.0004 This attribute defines the index (one based) of the
COO support information associated with the COO trouble ticket."
    ::= { cooTroubleTicketTableEntry 4 }
cooTroubleTicketNumberName                      OBJECT-TYPE
    SYNTAX      DellCostofOwnershipString
    ACCESS      read-write
    STATUS      mandatory
    DESCRIPTION
"1600.0110.0001.0005 This attribute defines the name of the
COO trouble ticket."
    ::= { cooTroubleTicketTableEntry 5 }


-------------------------------------------------------------------------------
-- Remote Access Group (in another MIB file)
--
-- OID Format: 1.3.6.1.4.1.674.10892.1.1700
-------------------------------------------------------------------------------


-------------------------------------------------------------------------------
-- Cluster Group
--
-- OID Format: 1.3.6.1.4.1.674.10892.1.1800
-------------------------------------------------------------------------------


-------------------------------------------------------------------------------
-- Cluster Table
--
-- OID Format: 1.3.6.1.4.1.674.10892.1.1800.10.1.<a>.<i1>.<i2>
-------------------------------------------------------------------------------

DellClusterType                                 ::= INTEGER {
    unknown(1),                                 -- cluster type is unknown
    highAvailabilityCluster(2)                  -- cluster type is High Availability Cluster
}

ClusterTableEntry                               ::= SEQUENCE {
    clusterChassisIndex                         DellObjectRange,
    clusterIndex                                DellObjectRange,
    clusterStateCapabilities                    DellStateCapabilities,
    clusterStateSettings                        DellStateSettings,
    clusterStatus                               DellStatus,
    clusterType                                 DellClusterType,
    clusterTypeDescriptionName                  DellString,
    clusterName                                 DellString
}

clusterTable                                    OBJECT-TYPE
    SYNTAX      SEQUENCE OF ClusterTableEntry
    ACCESS      not-accessible
    STATUS      mandatory
    DESCRIPTION
"1800.0010 This object defines the Cluster Table."
    ::= { clusterGroup 10 }
clusterTableEntry                               OBJECT-TYPE
    SYNTAX      ClusterTableEntry
    ACCESS      not-accessible
    STATUS      mandatory
    DESCRIPTION
"1800.0010.0001 This object defines the Cluster Table Entry."
    INDEX       { clusterChassisIndex,
                  clusterIndex }
    ::= { clusterTable 1 }

clusterChassisIndex                             OBJECT-TYPE
    SYNTAX      DellObjectRange
    ACCESS      read-only
    STATUS      mandatory
    DESCRIPTION
"1800.0010.0001.0001 This attribute defines the index (one based) of the
associated chassis."
    ::= { clusterTableEntry 1 }
clusterIndex                                    OBJECT-TYPE
    SYNTAX      DellObjectRange
    ACCESS      read-only
    STATUS      mandatory
    DESCRIPTION
"1800.0010.0001.0002 This attribute defines the index (one based) of the
cluster."
    ::= { clusterTableEntry 2 }
clusterStateCapabilities                        OBJECT-TYPE
    SYNTAX      DellStateCapabilities
    ACCESS      read-only
    STATUS      mandatory
    DESCRIPTION
"1800.0010.0001.0003 This attribute defines the state capabilities of the
cluster."
    ::= { clusterTableEntry 3 }
clusterStateSettings                            OBJECT-TYPE
    SYNTAX      DellStateSettings
    ACCESS      read-write
    STATUS      mandatory
    DESCRIPTION
"1800.0010.0001.0004 This attribute defines the state settings of the
 cluster."
    ::= { clusterTableEntry 4 }
clusterStatus                                   OBJECT-TYPE
    SYNTAX      DellStatus
    ACCESS      read-only
    STATUS      mandatory
    DESCRIPTION
"1800.0010.0001.0005 This attribute defines the status of the cluster."
    ::= { clusterTableEntry 5 }
clusterType                                     OBJECT-TYPE
    SYNTAX      DellClusterType
    ACCESS      read-only
    STATUS      mandatory
    DESCRIPTION
"1800.0010.0001.0006 This attribute defines the type of the cluster."
    ::= { clusterTableEntry 6 }
clusterTypeDescriptionName                      OBJECT-TYPE
    SYNTAX      DellString
    ACCESS      read-only
    STATUS      mandatory
    DESCRIPTION
"1800.0010.0001.0007 This attribute defines the description name for the
type of the cluster."
    ::= { clusterTableEntry 7 }
clusterName                                     OBJECT-TYPE
    SYNTAX      DellString
    ACCESS      read-only
    STATUS      mandatory
    DESCRIPTION
"1800.0010.0001.0008 This attribute defines the name of the cluster."
    ::= { clusterTableEntry 8 }


-------------------------------------------------------------------------------
-- Baseboard Management Controller (BMC) Group
--
-- OID Format: 1.3.6.1.4.1.674.10892.1.1900
-------------------------------------------------------------------------------


-------------------------------------------------------------------------------
-- Baseboard Management Controller (BMC) Table
--
-- OID Format: 1.3.6.1.4.1.674.10892.1.1900.10.1.<a>.<i1>.<i2>
-------------------------------------------------------------------------------

DellManagementControllerType                    ::= INTEGER {
    -- legacyBMC(0),                            -  type is legacy Baseboard Management Controller
    iDRAC(8),                                   -- type is Integrated Dell Remote Access Controller
    iDRAC6(10),                                 -- type is Integrated Dell Remote Access Controller 6
    iDRAC6Modular(11),                          -- type is Integrated Dell Remote Access Controller 6 (Modular)
    iDRAC6BMC(13)                               -- type is Integrated Dell Remote Access Controller 6 (BMC mode)
}

BmcTableEntry                                   ::= SEQUENCE {
    bmcChassisIndex                             DellObjectRange,
    bmcIndex                                    DellObjectRange,
    bmcStateCapabilities                        DellStateCapabilities,
    bmcStateSettings                            DellStateSettings,
    bmcStatus                                   DellStatus,
    bmcDisplayName                              DellString,
    bmcDescriptionName                          DisplayString (SIZE (0..255)),
    bmcIPMIVersionName                          DellString,
    bmcGUID                                     OCTET STRING (SIZE(16)),
    bmcType                                     DellManagementControllerType,
    bmcModuleName                               DellString,
    bmcIPv4URLName                              DisplayString (SIZE (0..1024)),
    bmcIPv6URLName                              DisplayString (SIZE (0..1024))
}

bmcTable                                        OBJECT-TYPE
    SYNTAX      SEQUENCE OF BmcTableEntry
    ACCESS      not-accessible
    STATUS      mandatory
    DESCRIPTION
"1900.0010 This object defines the Baseboard Management Controller (BMC)
Table."
    ::= { bmcGroup 10 }
bmcTableEntry                                   OBJECT-TYPE
    SYNTAX      BmcTableEntry
    ACCESS      not-accessible
    STATUS      mandatory
    DESCRIPTION
"1900.0010.0001 This object defines the Baseboard Management Controller (BMC)
Table Entry."
    INDEX       { bmcChassisIndex,
                  bmcIndex }
    ::= { bmcTable 1 }

bmcChassisIndex                                 OBJECT-TYPE
    SYNTAX      DellObjectRange
    ACCESS      read-only
    STATUS      mandatory
    DESCRIPTION
"1900.0010.0001.0001 This attribute defines the index (one based) of the
associated chassis."
    ::= { bmcTableEntry 1 }
bmcIndex                                        OBJECT-TYPE
    SYNTAX      DellObjectRange
    ACCESS      read-only
    STATUS      mandatory
    DESCRIPTION
"1900.0010.0001.0002 This attribute defines the index (one based) of the BMC."
    ::= { bmcTableEntry 2 }
bmcStateCapabilities                            OBJECT-TYPE
    SYNTAX      DellStateCapabilities
    ACCESS      read-only
    STATUS      mandatory
    DESCRIPTION
"1900.0010.0001.0003 This attribute defines the state capabilities of the BMC."
    ::= { bmcTableEntry 3 }
bmcStateSettings                                OBJECT-TYPE
    SYNTAX      DellStateSettings
    ACCESS      read-write
    STATUS      mandatory
    DESCRIPTION
"1900.0010.0001.0004 This attribute defines the state settings of the BMC."
    ::= { bmcTableEntry 4 }
bmcStatus                                       OBJECT-TYPE
    SYNTAX      DellStatus
    ACCESS      read-only
    STATUS      mandatory
    DESCRIPTION
"1900.0010.0001.0005 This attribute defines the status of the BMC."
    ::= { bmcTableEntry 5 }
bmcDisplayName                                  OBJECT-TYPE
    SYNTAX      DellString
    ACCESS      read-only
    STATUS      mandatory
    DESCRIPTION
"1900.0010.0001.0006 This attribute defines the display name of the BMC."
    ::= { bmcTableEntry 6 }
bmcDescriptionName                              OBJECT-TYPE
    SYNTAX      DisplayString (SIZE (0..255))
    ACCESS      read-only
    STATUS      mandatory
    DESCRIPTION
"1900.0010.0001.0007 This attribute defines the description of the BMC."
    ::= { bmcTableEntry 7 }
bmcIPMIVersionName                              OBJECT-TYPE
    SYNTAX      DellString
    ACCESS      read-only
    STATUS      mandatory
    DESCRIPTION
"1900.0010.0001.0008 This attribute defines the version of the
Intelligent Platform Management Interface (IPMI) specification
that the BMC supports."
    ::= { bmcTableEntry 8 }
bmcGUID                                         OBJECT-TYPE
    SYNTAX      OCTET STRING (SIZE(16))
    ACCESS      read-only
    STATUS      mandatory
    DESCRIPTION
"1900.0010.0001.0009 This attribute defines the Globally Unique ID (GUID)
of the BMC."
    ::= { bmcTableEntry 9 }
bmcType                                         OBJECT-TYPE
    SYNTAX      DellManagementControllerType
    ACCESS      read-only
    STATUS      mandatory
    DESCRIPTION
"1900.0010.0001.00010 This attribute defines the type of the BMC."
    ::= { bmcTableEntry 10 }
bmcModuleName                                   OBJECT-TYPE
    SYNTAX      DellString
    ACCESS      read-only
    STATUS      mandatory
    DESCRIPTION
"1900.0010.0001.0011 This attribute defines the module name for the BMC.
The module name is present only on certain systems such as blade systems."
    ::= { bmcTableEntry 11 }
bmcIPv4URLName                                  OBJECT-TYPE
    SYNTAX      DisplayString (SIZE (0..1024))
    ACCESS      read-only
    STATUS      mandatory
    DESCRIPTION
"1900.0010.0001.0012 This attribute defines the IPv4 URL for the BMC.
The URL is not present on all systems."
    ::= { bmcTableEntry 12 }
bmcIPv6URLName                                  OBJECT-TYPE
    SYNTAX      DisplayString (SIZE (0..1024))
    ACCESS      read-only
    STATUS      mandatory
    DESCRIPTION
"1900.0010.0001.0013 This attribute defines the IPv6 URL for the BMC.
The URL is not present on all systems."
    ::= { bmcTableEntry 13 }


-------------------------------------------------------------------------------
-- Baseboard Management Controller (BMC) Serial Interface Table
--
-- OID Format: 1.3.6.1.4.1.674.10892.1.1900.20.1.<a>.<i1>.<i2>.<i3>
-------------------------------------------------------------------------------

DellBMCSerialConnectionModeCapabilities         ::= INTEGER {
    -- Note: These values are bit masks, so combination values are possible.
    -- none(0),                                 -  no mode capabilities
    modemBasic(1),                              -- Modem Basic mode capable
    modemPPP(2),                                -- Modem PPP mode capable
    modemTerminal(4),                           -- Modem Terminal mode capable
    directBasic(8),                             -- Direct Basic mode capable
    directPPP(16),                              -- Direct PPP mode capable
    directTerminal(32)                          -- Direct Terminal mode capable
}
DellBMCSerialConnectionModeSettings             ::= INTEGER {
    -- Note: These values are bit masks, so combination values are possible.
    -- none(0),                                 -  no modes enabled
    modemBasic(1),                              -- Modem Basic mode enabled
    modemPPP(2),                                -- Modem PPP mode enabled
    modemTerminal(4),                           -- Modem Terminal mode enabled
    directBasic(8),                             -- Direct Basic mode enabled
    directPPP(16),                              -- Direct PPP mode enabled
    directTerminal(32)                          -- Direct Terminal mode enabled
}
DellBMCSerialFlowControlType                    ::= INTEGER {
    -- none(0),                                 -  no flow control used
    rtsCts(1),                                  -- RTS/CTS (hardware) flow control
    xonXoff(2)                                  -- XON/XOFF flow control
}
DellBMCSerialBitRateType                        ::= INTEGER {
    bps9600(6),                                 -- 9600 bps (bits per second)
    bps19200(7),                                -- 19200 bps
    bps38400(8),                                -- 38400 bps
    bps57600(9),                                -- 57600 bps
    bps115200(10)                               -- 115200 bps
}

BmcSerialInterfaceTableEntry                    ::= SEQUENCE {
    bmcSerialInterfaceChassisIndex              DellObjectRange,
    bmcSerialInterfaceBMCIndex                  DellObjectRange,
    bmcSerialInterfaceIndex                     DellObjectRange,
    bmcSerialInterfaceStateCapabilities         DellStateCapabilities,
    bmcSerialInterfaceStateSettings             DellStateSettings,
    bmcSerialInterfaceStatus                    DellStatus,
    bmcSerialInterfaceChannelNumber             DellUnsigned8BitRange,
    bmcSerialInterfaceConnectionModeCapabilities DellBMCSerialConnectionModeCapabilities,
    bmcSerialInterfaceConnectionModeSettings    DellBMCSerialConnectionModeSettings,
    bmcSerialInterfaceFlowControl               DellBMCSerialFlowControlType,
    bmcSerialInterfaceBitRate                   DellBMCSerialBitRateType
}

bmcSerialInterfaceTable                         OBJECT-TYPE
    SYNTAX      SEQUENCE OF BmcSerialInterfaceTableEntry
    ACCESS      not-accessible
    STATUS      mandatory
    DESCRIPTION
"1900.0020 This object defines the Baseboard Management Controller (BMC)
Serial Interface Table."
    ::= { bmcGroup 20 }
bmcSerialInterfaceTableEntry                    OBJECT-TYPE
    SYNTAX      BmcSerialInterfaceTableEntry
    ACCESS      not-accessible
    STATUS      mandatory
    DESCRIPTION
"1900.0020.0001 This object defines the Baseboard Management Controller (BMC)
Serial Interface Table Entry."
    INDEX       { bmcSerialInterfaceChassisIndex,
                  bmcSerialInterfaceBMCIndex,
                  bmcSerialInterfaceIndex }
    ::= { bmcSerialInterfaceTable 1 }

bmcSerialInterfaceChassisIndex                  OBJECT-TYPE
    SYNTAX      DellObjectRange
    ACCESS      read-only
    STATUS      mandatory
    DESCRIPTION
"1900.0020.0001.0001 This attribute defines the index (one based) of the
associated chassis."
    ::= { bmcSerialInterfaceTableEntry 1 }
bmcSerialInterfaceBMCIndex                      OBJECT-TYPE
    SYNTAX      DellObjectRange
    ACCESS      read-only
    STATUS      mandatory
    DESCRIPTION
"1900.0020.0001.0002 This attribute defines the index (one based) of the
assoiciated BMC."
    ::= { bmcSerialInterfaceTableEntry 2 }
bmcSerialInterfaceIndex                         OBJECT-TYPE
    SYNTAX      DellObjectRange
    ACCESS      read-only
    STATUS      mandatory
    DESCRIPTION
"1900.0020.0001.0003 This attribute defines the index (one based) of the
BMC serial interface."
    ::= { bmcSerialInterfaceTableEntry 3 }
bmcSerialInterfaceStateCapabilities             OBJECT-TYPE
    SYNTAX      DellStateCapabilities
    ACCESS      read-only
    STATUS      mandatory
    DESCRIPTION
"1900.0020.0001.0004 This attribute defines the state capabilities of the
BMC serial interface."
    ::= { bmcSerialInterfaceTableEntry 4 }
bmcSerialInterfaceStateSettings                 OBJECT-TYPE
    SYNTAX      DellStateSettings
    ACCESS      read-write
    STATUS      mandatory
    DESCRIPTION
"1900.0020.0001.0005 This attribute defines the state settings of the
BMC serial interface."
    ::= { bmcSerialInterfaceTableEntry 5 }
bmcSerialInterfaceStatus                        OBJECT-TYPE
    SYNTAX      DellStatus
    ACCESS      read-only
    STATUS      mandatory
    DESCRIPTION
"1900.0020.0001.0006 This attribute defines the status of the
BMC serial interface."
    ::= { bmcSerialInterfaceTableEntry 6 }
bmcSerialInterfaceChannelNumber                 OBJECT-TYPE
    SYNTAX      DellUnsigned8BitRange
    ACCESS      read-only
    STATUS      mandatory
    DESCRIPTION
"1900.0020.0001.0007 This attribute defines the BMC channel number of the
BMC serial interface."
    ::= { bmcSerialInterfaceTableEntry 7 }
bmcSerialInterfaceConnectionModeCapabilities    OBJECT-TYPE
    SYNTAX      DellBMCSerialConnectionModeCapabilities
    ACCESS      read-only
    STATUS      mandatory
    DESCRIPTION
"1900.0020.0001.0008 This attribute defines the connection mode capabilities
of the BMC serial interface."
    ::= { bmcSerialInterfaceTableEntry 8 }
bmcSerialInterfaceConnectionModeSettings        OBJECT-TYPE
    SYNTAX      DellBMCSerialConnectionModeSettings
    ACCESS      read-only
    STATUS      mandatory
    DESCRIPTION
"1900.0020.0001.0009 This attribute defines the connection mode settings
of the BMC serial interface."
    ::= { bmcSerialInterfaceTableEntry 9 }
bmcSerialInterfaceFlowControl                   OBJECT-TYPE
    SYNTAX      DellBMCSerialFlowControlType
    ACCESS      read-only
    STATUS      mandatory
    DESCRIPTION
"1900.0020.0001.0010 This attribute defines the flow control type of the
BMC serial interface."
    ::= { bmcSerialInterfaceTableEntry 10 }
bmcSerialInterfaceBitRate                       OBJECT-TYPE
    SYNTAX      DellBMCSerialBitRateType
    ACCESS      read-only
    STATUS      mandatory
    DESCRIPTION
"1900.0020.0001.0011 This attribute defines the bit rate of the
BMC serial interface."
    ::= { bmcSerialInterfaceTableEntry 11 }


-------------------------------------------------------------------------------
-- Baseboard Management Controller (BMC) LAN Interface Table
--
-- OID Format: 1.3.6.1.4.1.674.10892.1.1900.30.1.<a>.<i1>.<i2>.<i3>
-------------------------------------------------------------------------------

DellBMCLANIPAddressSourceType                   ::= INTEGER {
    -- unspecified(0),                          -  source is unspecified
    static(1),                                  -- static IP address
    dhcp(2),                                    -- DHCP used to obtain IP address
    biosOrSystemSoftware(3),                    -- BIOS or system software provided IP Address
    other(4)                                    -- other protocol used to obtain IP address
}

BmcLANInterfaceTableEntry                       ::= SEQUENCE {
    bmcLANInterfaceChassisIndex                 DellObjectRange,
    bmcLANInterfaceBMCIndex                     DellObjectRange,
    bmcLANInterfaceIndex                        DellObjectRange,
    bmcLANInterfaceStateCapabilities            DellStateCapabilities,
    bmcLANInterfaceStateSettings                DellStateSettings,
    bmcLANInterfaceStatus                       DellStatus,
    bmcLANInterfaceChannelNumber                DellUnsigned8BitRange,
    bmcLANInterfaceIPAddressSource              DellBMCLANIPAddressSourceType,
    bmcLANInterfaceIPAddress                    IpAddress,
    bmcLANInterfaceSubnetMaskAddress            IpAddress,
    bmcLANInterfaceDefaultGatewayAddress        IpAddress,
    bmcLANInterfaceMACAddress                   DellMACAddress,
    bmcLANInterfaceAlertCommunityName           DisplayString (SIZE (0..32))
}

bmcLANInterfaceTable                            OBJECT-TYPE
    SYNTAX      SEQUENCE OF BmcLANInterfaceTableEntry
    ACCESS      not-accessible
    STATUS      mandatory
    DESCRIPTION
"1900.0030 This object defines the Baseboard Management Controller (BMC)
LAN Interface Table."
    ::= { bmcGroup 30 }
bmcLANInterfaceTableEntry                       OBJECT-TYPE
    SYNTAX      BmcLANInterfaceTableEntry
    ACCESS      not-accessible
    STATUS      mandatory
    DESCRIPTION
"1900.0030.0001 This object defines the Baseboard Management Controller (BMC)
LAN Interface Table Entry."
    INDEX       { bmcLANInterfaceChassisIndex,
                  bmcLANInterfaceBMCIndex,
                  bmcLANInterfaceIndex }
    ::= { bmcLANInterfaceTable 1 }

bmcLANInterfaceChassisIndex                     OBJECT-TYPE
    SYNTAX      DellObjectRange
    ACCESS      read-only
    STATUS      mandatory
    DESCRIPTION
"1900.0030.0001.0001 This attribute defines the index (one based) of the
associated chassis."
    ::= { bmcLANInterfaceTableEntry 1 }
bmcLANInterfaceBMCIndex                         OBJECT-TYPE
    SYNTAX      DellObjectRange
    ACCESS      read-only
    STATUS      mandatory
    DESCRIPTION
"1900.0030.0001.0002 This attribute defines the index (one based) of the
assoiciated BMC."
    ::= { bmcLANInterfaceTableEntry 2 }
bmcLANInterfaceIndex                            OBJECT-TYPE
    SYNTAX      DellObjectRange
    ACCESS      read-only
    STATUS      mandatory
    DESCRIPTION
"1900.0030.0001.0003 This attribute defines the index (one based) of the
BMC LAN interface."
    ::= { bmcLANInterfaceTableEntry 3 }
bmcLANInterfaceStateCapabilities                OBJECT-TYPE
    SYNTAX      DellStateCapabilities
    ACCESS      read-only
    STATUS      mandatory
    DESCRIPTION
"1900.0030.0001.0004 This attribute defines the state capabilities of the
BMC LAN interface."
    ::= { bmcLANInterfaceTableEntry 4 }
bmcLANInterfaceStateSettings                    OBJECT-TYPE
    SYNTAX      DellStateSettings
    ACCESS      read-write
    STATUS      mandatory
    DESCRIPTION
"1900.0030.0001.0005 This attribute defines the state settings of the
BMC LAN interface."
    ::= { bmcLANInterfaceTableEntry 5 }
bmcLANInterfaceStatus                           OBJECT-TYPE
    SYNTAX      DellStatus
    ACCESS      read-only
    STATUS      mandatory
    DESCRIPTION
"1900.0030.0001.0006 This attribute defines the status of the
BMC LAN interface."
    ::= { bmcLANInterfaceTableEntry 6 }
bmcLANInterfaceChannelNumber                    OBJECT-TYPE
    SYNTAX      DellUnsigned8BitRange
    ACCESS      read-only
    STATUS      mandatory
    DESCRIPTION
"1900.0030.0001.0007 This attribute defines the BMC channel number of the
BMC LAN interface."
    ::= { bmcLANInterfaceTableEntry 7 }
bmcLANInterfaceIPAddressSource                  OBJECT-TYPE
    SYNTAX      DellBMCLANIPAddressSourceType
    ACCESS      read-only
    STATUS      mandatory
    DESCRIPTION
"1900.0030.0001.0008 This attribute defines the source type of the
IP address of the BMC LAN interface."
    ::= { bmcLANInterfaceTableEntry 8 }
bmcLANInterfaceIPAddress                        OBJECT-TYPE
    SYNTAX      IpAddress
    ACCESS      read-only
    STATUS      mandatory
    DESCRIPTION
"1900.0030.0001.0009 This attribute defines the IP address of the
BMC LAN interface."
    ::= { bmcLANInterfaceTableEntry 9 }
bmcLANInterfaceSubnetMaskAddress                OBJECT-TYPE
    SYNTAX      IpAddress
    ACCESS      read-only
    STATUS      mandatory
    DESCRIPTION
"1900.0030.0001.0010 This attribute defines the subnet mask of the
BMC LAN interface."
    ::= { bmcLANInterfaceTableEntry 10 }
bmcLANInterfaceDefaultGatewayAddress            OBJECT-TYPE
    SYNTAX      IpAddress
    ACCESS      read-only
    STATUS      mandatory
    DESCRIPTION
"1900.0030.0001.0011 This attribute defines the IP address of the
default gateway for the BMC LAN interface."
    ::= { bmcLANInterfaceTableEntry 11 }
bmcLANInterfaceMACAddress                       OBJECT-TYPE
    SYNTAX      DellMACAddress
    ACCESS      read-only
    STATUS      mandatory
    DESCRIPTION
"1900.0030.0001.0012 This attribute defines the MAC address of the
BMC LAN interface."
    ::= { bmcLANInterfaceTableEntry 12 }
bmcLANInterfaceAlertCommunityName               OBJECT-TYPE
    SYNTAX      DisplayString (SIZE (0..32))
    ACCESS      read-only
    STATUS      mandatory
    DESCRIPTION
"1900.0030.0001.0013 This attribute defines the SNMP community used for
BMC LAN alerts (traps) sent on the BMC LAN interface."
    ::= { bmcLANInterfaceTableEntry 13 }


-------------------------------------------------------------------------------
-- Alert Group
--
-- OID Format: 1.3.6.1.4.1.674.10892.1.5000
-------------------------------------------------------------------------------

alertVariables                  OBJECT IDENTIFIER ::= { alertGroup     10    }


-------------------------------------------------------------------------------
-- Alert Variables
--
-- OID Format: 1.3.6.1.4.1.674.10892.1.5000.10.<a>.0
-------------------------------------------------------------------------------

alertSystem                                     OBJECT-TYPE
    SYNTAX      DisplayString (SIZE (0..255))
    ACCESS      read-only
    STATUS      mandatory
    DESCRIPTION
"5000.0010.0001 Name of the system generating the alert."
    ::= { alertVariables 1 }
alertTableIndexOID                              OBJECT-TYPE
    SYNTAX      OBJECT IDENTIFIER
    ACCESS      read-only
    STATUS      mandatory
    DESCRIPTION
"5000.0010.0002 OID for the index attribute in the table that contains the object
causing the alert.  This value can be used to uniquely identify the object
causing the alert and to correlate different alerts caused by an object.
If not applicable, the value will be 0.0."
    ::= { alertVariables 2 }
alertMessage                                    OBJECT-TYPE
    SYNTAX      DisplayString (SIZE (0..1024))
    ACCESS      read-only
    STATUS      mandatory
    DESCRIPTION
"5000.0010.0003 Message describing the alert."
    ::= { alertVariables 3 }
alertCurrentStatus                              OBJECT-TYPE
    SYNTAX      DellStatus
    ACCESS      read-only
    STATUS      mandatory
    DESCRIPTION
"5000.0010.0004 Current status of object causing the alert."
    ::= { alertVariables 4 }
alertPreviousStatus                             OBJECT-TYPE
    SYNTAX      DellStatus
    ACCESS      read-only
    STATUS      mandatory
    DESCRIPTION
"5000.0010.0005 Previous status of object causing the alert."
    ::= { alertVariables 5 }
alertData                                       OBJECT-TYPE
    SYNTAX      OCTET STRING (SIZE (0..1024))
    ACCESS      read-only
    STATUS      mandatory
    DESCRIPTION
"5000.0010.0006 Alert data."
    ::= { alertVariables 6 }


-------------------------------------------------------------------------------
--
-- Traps
--
-------------------------------------------------------------------------------


-------------------------------------------------------------------------------
-- Miscellaneous Traps
-------------------------------------------------------------------------------

alertSystemUp                                   TRAP-TYPE
    ENTERPRISE  baseboardGroup
    VARIABLES { alertSystem,
                alertTableIndexOID,
                alertMessage,
                alertCurrentStatus,
                alertPreviousStatus,
                alertData }
    DESCRIPTION
"Server Administrator has completed its initialization."

    --Novell NMS trap annotation
    --#TYPE       "Server Administrator Startup Complete"
    --#SUMMARY    "%s"
    --#ARGUMENTS  {2}
    --#SEVERITY   INFORMATIONAL
    --#TIMEINDEX  99
    --#STATE      OPERATIONAL

    ::= 1001

alertThermalShutdown                            TRAP-TYPE
    ENTERPRISE  baseboardGroup
    VARIABLES { alertSystem,
                alertTableIndexOID,
                alertMessage,
                alertCurrentStatus,
                alertPreviousStatus,
                alertData }
    DESCRIPTION
"Thermal shutdown protection has been initiated."

    --Novell NMS trap annotation
    --#TYPE       "Server Thermal Shutdown"
    --#SUMMARY    "%s"
    --#ARGUMENTS  {2}
    --#SEVERITY   CRITICAL
    --#TIMEINDEX  99
    --#STATE      NONOPERATIONAL

    ::= 1004

alertAutomaticSystemRecovery                    TRAP-TYPE
    ENTERPRISE  baseboardGroup
    VARIABLES { alertSystem,
                alertTableIndexOID,
                alertMessage,
                alertCurrentStatus,
                alertPreviousStatus,
                alertData }
    DESCRIPTION
"Automatic system recovery (ASR) was performed."

    --Novell NMS trap annotation
    --#TYPE       "Server Automatic System Recovery"
    --#SUMMARY    "%s"
    --#ARGUMENTS  {2}
    --#SEVERITY   CRITICAL
    --#TIMEINDEX  99
    --#STATE      OPERATIONAL

    ::= 1006

alertUserHostSystemReset                        TRAP-TYPE
    ENTERPRISE  baseboardGroup
    VARIABLES { alertSystem,
                alertTableIndexOID,
                alertMessage,
                alertCurrentStatus,
                alertPreviousStatus,
                alertData }
    DESCRIPTION
"User has initiated host system reset."

    --Novell NMS trap annotation
    --#TYPE       "Server User Host System Reset"
    --#SUMMARY    "%s"
    --#ARGUMENTS  {2}
    --#SEVERITY   INFORMATIONAL
    --#TIMEINDEX  99
    --#STATE      OPERATIONAL

    ::= 1007

alertSystemPeakPowerNewPeak                     TRAP-TYPE
    ENTERPRISE  baseboardGroup
    VARIABLES { alertSystem,
                alertTableIndexOID,
                alertMessage,
                alertCurrentStatus,
                alertPreviousStatus,
                alertData }
    DESCRIPTION
"System peak power sensor has detected a new peak value."

    --Novell NMS trap annotation
    --#TYPE       "Server System Peak Power New Peak"
    --#SUMMARY    "%s"
    --#ARGUMENTS  {2}
    --#SEVERITY   INFORMATIONAL
    --#TIMEINDEX  99
    --#STATE      OPERATIONAL

    ::= 1013

alertSystemSoftwareEvent                        TRAP-TYPE
    ENTERPRISE  baseboardGroup
    VARIABLES { alertSystem,
                alertTableIndexOID,
                alertMessage,
                alertCurrentStatus,
                alertPreviousStatus,
                alertData }
    DESCRIPTION
"System software event has occurred."

    --Novell NMS trap annotation
    --#TYPE       "Server System Software Event"
    --#SUMMARY    "%s"
    --#ARGUMENTS  {2}
    --#SEVERITY   MINOR
    --#TIMEINDEX  99
    --#STATE      OPERATIONAL

    ::= 1014

-------------------------------------------------------------------------------
-- Temperature Probe Traps
-------------------------------------------------------------------------------

alertTemperatureProbeNormal                     TRAP-TYPE
    ENTERPRISE  baseboardGroup
    VARIABLES { alertSystem,
                alertTableIndexOID,
                alertMessage,
                alertCurrentStatus,
                alertPreviousStatus,
                alertData }
    DESCRIPTION
"Temperature probe has returned to a normal value."

    --Novell NMS trap annotation
    --#TYPE       "Server Temperature Normal"
    --#SUMMARY    "%s"
    --#ARGUMENTS  {2}
    --#SEVERITY   INFORMATIONAL
    --#TIMEINDEX  99
    --#STATE      OPERATIONAL

    ::= 1052

alertTemperatureProbeWarning                    TRAP-TYPE
    ENTERPRISE  baseboardGroup
    VARIABLES { alertSystem,
                alertTableIndexOID,
                alertMessage,
                alertCurrentStatus,
                alertPreviousStatus,
                alertData }
    DESCRIPTION
"Temperature probe has detected a warning value."

    --Novell NMS trap annotation
    --#TYPE       "Server Temperature Warning"
    --#SUMMARY    "%s"
    --#ARGUMENTS  {2}
    --#SEVERITY   MINOR
    --#TIMEINDEX  99
    --#STATE      DEGRADED

    ::= 1053

alertTemperatureProbeFailure                    TRAP-TYPE
    ENTERPRISE  baseboardGroup
    VARIABLES { alertSystem,
                alertTableIndexOID,
                alertMessage,
                alertCurrentStatus,
                alertPreviousStatus,
                alertData }
    DESCRIPTION
"Temperature probe has detected a failure value."

    --Novell NMS trap annotation
    --#TYPE       "Server Temperature Failure"
    --#SUMMARY    "%s"
    --#ARGUMENTS  {2}
    --#SEVERITY   CRITICAL
    --#TIMEINDEX  99
    --#STATE      DEGRADED

    ::= 1054

alertTemperatureProbeNonRecoverable             TRAP-TYPE
    ENTERPRISE  baseboardGroup
    VARIABLES { alertSystem,
                alertTableIndexOID,
                alertMessage,
                alertCurrentStatus,
                alertPreviousStatus,
                alertData }
    DESCRIPTION
"Temperature probe has detected a non-recoverable value."

    --Novell NMS trap annotation
    --#TYPE       "Server Temperature Nonrecoverable"
    --#SUMMARY    "%s"
    --#ARGUMENTS  {2}
    --#SEVERITY   CRITICAL
    --#TIMEINDEX  99
    --#STATE      DEGRADED

    ::= 1055

-------------------------------------------------------------------------------
-- Cooling Device Traps
-------------------------------------------------------------------------------

alertCoolingDeviceNormal                        TRAP-TYPE
    ENTERPRISE  baseboardGroup
    VARIABLES { alertSystem,
                alertTableIndexOID,
                alertMessage,
                alertCurrentStatus,
                alertPreviousStatus,
                alertData }
    DESCRIPTION
"Cooling device sensor has returned to a normal value."

    --Novell NMS trap annotation
    --#TYPE       "Server Cooling Device Normal"
    --#SUMMARY    "%s"
    --#ARGUMENTS  {2}
    --#SEVERITY   INFORMATIONAL
    --#TIMEINDEX  99
    --#STATE      OPERATIONAL

    ::= 1102

alertCoolingDeviceWarning                       TRAP-TYPE
    ENTERPRISE  baseboardGroup
    VARIABLES { alertSystem,
                alertTableIndexOID,
                alertMessage,
                alertCurrentStatus,
                alertPreviousStatus,
                alertData }
    DESCRIPTION
"Cooling device sensor has detected a warning value."

    --Novell NMS trap annotation
    --#TYPE       "Server Cooling Device Warning"
    --#SUMMARY    "%s"
    --#ARGUMENTS  {2}
    --#SEVERITY   MINOR
    --#TIMEINDEX  99
    --#STATE      DEGRADED

    ::= 1103

alertCoolingDeviceFailure                       TRAP-TYPE
    ENTERPRISE  baseboardGroup
    VARIABLES { alertSystem,
                alertTableIndexOID,
                alertMessage,
                alertCurrentStatus,
                alertPreviousStatus,
                alertData }
    DESCRIPTION
"Cooling device sensor has detected a failure value."

    --Novell NMS trap annotation
    --#TYPE       "Server Cooling Device Failure"
    --#SUMMARY    "%s"
    --#ARGUMENTS  {2}
    --#SEVERITY   CRITICAL
    --#TIMEINDEX  99
    --#STATE      DEGRADED

    ::= 1104

alertCoolingDeviceNonRecoverable                TRAP-TYPE
    ENTERPRISE  baseboardGroup
    VARIABLES { alertSystem,
                alertTableIndexOID,
                alertMessage,
                alertCurrentStatus,
                alertPreviousStatus,
                alertData }
    DESCRIPTION
"Cooling device sensor has detected a non-recoverable value."

    --Novell NMS trap annotation
    --#TYPE       "Server Cooling Device Nonrecoverable"
    --#SUMMARY    "%s"
    --#ARGUMENTS  {2}
    --#SEVERITY   CRITICAL
    --#TIMEINDEX  99
    --#STATE      DEGRADED

    ::= 1105

-------------------------------------------------------------------------------
-- Voltage Probe Traps
-------------------------------------------------------------------------------

alertVoltageProbeNormal                         TRAP-TYPE
    ENTERPRISE  baseboardGroup
    VARIABLES { alertSystem,
                alertTableIndexOID,
                alertMessage,
                alertCurrentStatus,
                alertPreviousStatus,
                alertData }
    DESCRIPTION
"Voltage probe has returned to a normal value."

    --Novell NMS trap annotation
    --#TYPE       "Server Voltage Normal"
    --#SUMMARY    "%s"
    --#ARGUMENTS  {2}
    --#SEVERITY   INFORMATIONAL
    --#TIMEINDEX  99
    --#STATE      OPERATIONAL

    ::= 1152

alertVoltageProbeWarning                        TRAP-TYPE
    ENTERPRISE  baseboardGroup
    VARIABLES { alertSystem,
                alertTableIndexOID,
                alertMessage,
                alertCurrentStatus,
                alertPreviousStatus,
                alertData }
    DESCRIPTION
"Voltage probe has detected a warning value."

    --Novell NMS trap annotation
    --#TYPE       "Server Voltage Warning"
    --#SUMMARY    "%s"
    --#ARGUMENTS  {2}
    --#SEVERITY   MINOR
    --#TIMEINDEX  99
    --#STATE      DEGRADED

    ::= 1153

alertVoltageProbeFailure                        TRAP-TYPE
    ENTERPRISE  baseboardGroup
    VARIABLES { alertSystem,
                alertTableIndexOID,
                alertMessage,
                alertCurrentStatus,
                alertPreviousStatus,
                alertData }
    DESCRIPTION
"Voltage probe has detected a failure value."

    --Novell NMS trap annotation
    --#TYPE       "Server Voltage Failure"
    --#SUMMARY    "%s"
    --#ARGUMENTS  {2}
    --#SEVERITY   CRITICAL
    --#TIMEINDEX  99
    --#STATE      DEGRADED

    ::= 1154

alertVoltageProbeNonRecoverable                 TRAP-TYPE
    ENTERPRISE  baseboardGroup
    VARIABLES { alertSystem,
                alertTableIndexOID,
                alertMessage,
                alertCurrentStatus,
                alertPreviousStatus,
                alertData }
    DESCRIPTION
"Voltage probe has detected a non-recoverable value."

    --Novell NMS trap annotation
    --#TYPE       "Server Voltage Nonrecoverable"
    --#SUMMARY    "%s"
    --#ARGUMENTS  {2}
    --#SEVERITY   CRITICAL
    --#TIMEINDEX  99
    --#STATE      DEGRADED

    ::= 1155

-------------------------------------------------------------------------------
-- Amperage Probe Traps
-------------------------------------------------------------------------------

alertAmperageProbeNormal                        TRAP-TYPE
    ENTERPRISE  baseboardGroup
    VARIABLES { alertSystem,
                alertTableIndexOID,
                alertMessage,
                alertCurrentStatus,
                alertPreviousStatus,
                alertData }
    DESCRIPTION
"Amperage probe has returned to a normal value."

    --Novell NMS trap annotation
    --#TYPE       "Server Amperage Normal"
    --#SUMMARY    "%s"
    --#ARGUMENTS  {2}
    --#SEVERITY   INFORMATIONAL
    --#TIMEINDEX  99
    --#STATE      OPERATIONAL

    ::= 1202

alertAmperageProbeWarning                       TRAP-TYPE
    ENTERPRISE  baseboardGroup
    VARIABLES { alertSystem,
                alertTableIndexOID,
                alertMessage,
                alertCurrentStatus,
                alertPreviousStatus,
                alertData }
    DESCRIPTION
"Amperage probe has detected a warning value."

    --Novell NMS trap annotation
    --#TYPE       "Server Amperage Warning"
    --#SUMMARY    "%s"
    --#ARGUMENTS  {2}
    --#SEVERITY   MINOR
    --#TIMEINDEX  99
    --#STATE      DEGRADED

    ::= 1203

alertAmperageProbeFailure                       TRAP-TYPE
    ENTERPRISE  baseboardGroup
    VARIABLES { alertSystem,
                alertTableIndexOID,
                alertMessage,
                alertCurrentStatus,
                alertPreviousStatus,
                alertData }
    DESCRIPTION
"Amperage probe has detected a failure value."

    --Novell NMS trap annotation
    --#TYPE       "Server Amperage Failure"
    --#SUMMARY    "%s"
    --#ARGUMENTS  {2}
    --#SEVERITY   CRITICAL
    --#TIMEINDEX  99
    --#STATE      DEGRADED

    ::= 1204

alertAmperageProbeNonRecoverable                TRAP-TYPE
    ENTERPRISE  baseboardGroup
    VARIABLES { alertSystem,
                alertTableIndexOID,
                alertMessage,
                alertCurrentStatus,
                alertPreviousStatus,
                alertData }
    DESCRIPTION
"Amperage probe has detected a non-recoverable value."

    --Novell NMS trap annotation
    --#TYPE       "Server Amperage Nonrecoverable"
    --#SUMMARY    "%s"
    --#ARGUMENTS  {2}
    --#SEVERITY   CRITICAL
    --#TIMEINDEX  99
    --#STATE      DEGRADED

    ::= 1205

-------------------------------------------------------------------------------
-- Chassis Intrusion Traps
-------------------------------------------------------------------------------

alertChassisIntrusionNormal                     TRAP-TYPE
    ENTERPRISE  baseboardGroup
    VARIABLES { alertSystem,
                alertTableIndexOID,
                alertMessage,
                alertCurrentStatus,
                alertPreviousStatus,
                alertData }
    DESCRIPTION
"Chassis intrusion has returned to normal."

    --Novell NMS trap annotation
    --#TYPE       "Server Chassis Intrusion Normal"
    --#SUMMARY    "%s"
    --#ARGUMENTS  {2}
    --#SEVERITY   INFORMATIONAL
    --#TIMEINDEX  99
    --#STATE      OPERATIONAL

    ::= 1252

alertChassisIntrusionDetected                   TRAP-TYPE
    ENTERPRISE  baseboardGroup
    VARIABLES { alertSystem,
                alertTableIndexOID,
                alertMessage,
                alertCurrentStatus,
                alertPreviousStatus,
                alertData }
    DESCRIPTION
"Chassis intrusion has been detected."

    --Novell NMS trap annotation
    --#TYPE       "Server Chassis Intrusion Detected"
    --#SUMMARY    "%s"
    --#ARGUMENTS  {2}
    --#SEVERITY   CRITICAL
    --#TIMEINDEX  99
    --#STATE      OPERATIONAL

    ::= 1254

-------------------------------------------------------------------------------
-- Redundancy Traps
-------------------------------------------------------------------------------

alertRedundancyNormal                           TRAP-TYPE
    ENTERPRISE  baseboardGroup
    VARIABLES { alertSystem,
                alertTableIndexOID,
                alertMessage,
                alertCurrentStatus,
                alertPreviousStatus,
                alertData }
    DESCRIPTION
"Redundancy has returned to normal."

    --Novell NMS trap annotation
    --#TYPE       "Server Redundancy Normal"
    --#SUMMARY    "%s"
    --#ARGUMENTS  {2}
    --#SEVERITY   INFORMATIONAL
    --#TIMEINDEX  99
    --#STATE      OPERATIONAL

    ::= 1304

alertRedundancyDegraded                         TRAP-TYPE
    ENTERPRISE  baseboardGroup
    VARIABLES { alertSystem,
                alertTableIndexOID,
                alertMessage,
                alertCurrentStatus,
                alertPreviousStatus,
                alertData }
    DESCRIPTION
"Redundancy has been degraded."

    --Novell NMS trap annotation
    --#TYPE       "Server Redundancy Degraded"
    --#SUMMARY    "%s"
    --#ARGUMENTS  {2}
    --#SEVERITY   MINOR
    --#TIMEINDEX  99
    --#STATE      DEGRADED

    ::= 1305

alertRedundancyLost                             TRAP-TYPE
    ENTERPRISE  baseboardGroup
    VARIABLES { alertSystem,
                alertTableIndexOID,
                alertMessage,
                alertCurrentStatus,
                alertPreviousStatus,
                alertData }
    DESCRIPTION
"Redundancy has been lost."

    --Novell NMS trap annotation
    --#TYPE       "Server Redundancy Lost"
    --#SUMMARY    "%s"
    --#ARGUMENTS  {2}
    --#SEVERITY   MAJOR
    --#TIMEINDEX  99
    --#STATE      DEGRADED

    ::= 1306

-------------------------------------------------------------------------------
-- Power Supply Traps
-------------------------------------------------------------------------------

alertPowerSupplyNormal                          TRAP-TYPE
    ENTERPRISE  baseboardGroup
    VARIABLES { alertSystem,
                alertTableIndexOID,
                alertMessage,
                alertCurrentStatus,
                alertPreviousStatus,
                alertData }
    DESCRIPTION
"Power supply has returned to normal."

    --Novell NMS trap annotation
    --#TYPE       "Server Power Supply Normal"
    --#SUMMARY    "%s"
    --#ARGUMENTS  {2}
    --#SEVERITY   INFORMATIONAL
    --#TIMEINDEX  99
    --#STATE      OPERATIONAL

    ::= 1352

alertPowerSupplyWarning                         TRAP-TYPE
    ENTERPRISE  baseboardGroup
    VARIABLES { alertSystem,
                alertTableIndexOID,
                alertMessage,
                alertCurrentStatus,
                alertPreviousStatus,
                alertData }
    DESCRIPTION
"Power supply has detected a warning."

    --Novell NMS trap annotation
    --#TYPE       "Server Power Supply Warning"
    --#SUMMARY    "%s"
    --#ARGUMENTS  {2}
    --#SEVERITY   MINOR
    --#TIMEINDEX  99
    --#STATE      DEGRADED

    ::= 1353

alertPowerSupplyFailure                         TRAP-TYPE
    ENTERPRISE  baseboardGroup
    VARIABLES { alertSystem,
                alertTableIndexOID,
                alertMessage,
                alertCurrentStatus,
                alertPreviousStatus,
                alertData }
    DESCRIPTION
"Power supply has detected a failure."

    --Novell NMS trap annotation
    --#TYPE       "Server Power Supply Failure"
    --#SUMMARY    "%s"
    --#ARGUMENTS  {2}
    --#SEVERITY   CRITICAL
    --#TIMEINDEX  99
    --#STATE      DEGRADED

    ::= 1354

-------------------------------------------------------------------------------
-- Memory Device Traps
-------------------------------------------------------------------------------

alertMemoryDeviceWarning                        TRAP-TYPE
    ENTERPRISE  baseboardGroup
    VARIABLES { alertSystem,
                alertTableIndexOID,
                alertMessage,
                alertCurrentStatus,
                alertPreviousStatus,
                alertData }
    DESCRIPTION
"Memory device status is noncritical."

    --Novell NMS trap annotation
    --#TYPE       "Server Memory Device Noncritical"
    --#SUMMARY    "%s"
    --#ARGUMENTS  {2}
    --#SEVERITY   MINOR
    --#TIMEINDEX  99
    --#STATE      DEGRADED

    ::= 1403

alertMemoryDeviceFailure                        TRAP-TYPE
    ENTERPRISE  baseboardGroup
    VARIABLES { alertSystem,
                alertTableIndexOID,
                alertMessage,
                alertCurrentStatus,
                alertPreviousStatus,
                alertData }
    DESCRIPTION
"Memory device status is critical."

    --Novell NMS trap annotation
    --#TYPE       "Server Memory Device Critical"
    --#SUMMARY    "%s"
    --#ARGUMENTS  {2}
    --#SEVERITY   CRITICAL
    --#TIMEINDEX  99
    --#STATE      DEGRADED

    ::= 1404

alertMemoryDeviceNonRecoverable                 TRAP-TYPE
    ENTERPRISE  baseboardGroup
    VARIABLES { alertSystem,
                alertTableIndexOID,
                alertMessage,
                alertCurrentStatus,
                alertPreviousStatus,
                alertData }
    DESCRIPTION
"Memory device status is non-recoverable."

    --Novell NMS trap annotation
    --#TYPE       "Server Memory Device Nonrecoverable"
    --#SUMMARY    "%s"
    --#ARGUMENTS  {2}
    --#SEVERITY   CRITICAL
    --#TIMEINDEX  99
    --#STATE      DEGRADED

    ::= 1405

-------------------------------------------------------------------------------
-- Fan Enclosure Traps
-------------------------------------------------------------------------------

alertFanEnclosureInsertion                      TRAP-TYPE
    ENTERPRISE  baseboardGroup
    VARIABLES { alertSystem,
                alertTableIndexOID,
                alertMessage,
                alertCurrentStatus,
                alertPreviousStatus,
                alertData }
    DESCRIPTION
"Fan enclosure has been inserted into system."

    --Novell NMS trap annotation
    --#TYPE       "Server Fan Enclosure Insertion"
    --#SUMMARY    "%s"
    --#ARGUMENTS  {2}
    --#SEVERITY   INFORMATIONAL
    --#TIMEINDEX  99
    --#STATE      OPERATIONAL

    ::= 1452

alertFanEnclosureRemoval                        TRAP-TYPE
    ENTERPRISE  baseboardGroup
    VARIABLES { alertSystem,
                alertTableIndexOID,
                alertMessage,
                alertCurrentStatus,
                alertPreviousStatus,
                alertData }
    DESCRIPTION
"Fan enclosure has been removed from system."

    --Novell NMS trap annotation
    --#TYPE       "Server Fan Enclosure Removal"
    --#SUMMARY    "%s"
    --#ARGUMENTS  {2}
    --#SEVERITY   MINOR
    --#TIMEINDEX  99
    --#STATE      DEGRADED

    ::= 1453

alertFanEnclosureExtendedRemoval                TRAP-TYPE
    ENTERPRISE  baseboardGroup
    VARIABLES { alertSystem,
                alertTableIndexOID,
                alertMessage,
                alertCurrentStatus,
                alertPreviousStatus,
                alertData }
    DESCRIPTION
"Fan enclosure has been removed from system for an extended amount of time."

    --Novell NMS trap annotation
    --#TYPE       "Server Fan Enclosure Extended Removal"
    --#SUMMARY    "%s"
    --#ARGUMENTS  {2}
    --#SEVERITY   CRITICAL
    --#TIMEINDEX  99
    --#STATE      DEGRADED

    ::= 1454

-------------------------------------------------------------------------------
-- AC Power Cord Traps
-------------------------------------------------------------------------------

alertACPowerCordNoPowerNonRedundant             TRAP-TYPE
    ENTERPRISE  baseboardGroup
    VARIABLES { alertSystem,
                alertTableIndexOID,
                alertMessage,
                alertCurrentStatus,
                alertPreviousStatus,
                alertData }
    DESCRIPTION
"AC power cord does not have power, and the reduncancy mode
for its AC power switch has been set to non-redundant."

    --Novell NMS trap annotation
    --#TYPE       "Server AC Cord No Power Non-redundant"
    --#SUMMARY    "%s"
    --#ARGUMENTS  {2}
    --#SEVERITY   INFORMATIONAL
    --#TIMEINDEX  99
    --#STATE      OPERATIONAL

    ::= 1501

alertACPowerCordNormal                          TRAP-TYPE
    ENTERPRISE  baseboardGroup
    VARIABLES { alertSystem,
                alertTableIndexOID,
                alertMessage,
                alertCurrentStatus,
                alertPreviousStatus,
                alertData }
    DESCRIPTION
"AC power cord has regained power."

    --Novell NMS trap annotation
    --#TYPE       "Server AC Cord Normal"
    --#SUMMARY    "%s"
    --#ARGUMENTS  {2}
    --#SEVERITY   INFORMATIONAL
    --#TIMEINDEX  99
    --#STATE      OPERATIONAL

    ::= 1502

alertACPowerCordFailure                         TRAP-TYPE
    ENTERPRISE  baseboardGroup
    VARIABLES { alertSystem,
                alertTableIndexOID,
                alertMessage,
                alertCurrentStatus,
                alertPreviousStatus,
                alertData }
    DESCRIPTION
"AC power cord has lost power."

    --Novell NMS trap annotation
    --#TYPE       "Server AC Cord Failure"
    --#SUMMARY    "%s"
    --#ARGUMENTS  {2}
    --#SEVERITY   CRITICAL
    --#TIMEINDEX  99
    --#STATE      DEGRADED

    ::= 1504

-------------------------------------------------------------------------------
-- Hardware Log Traps
-------------------------------------------------------------------------------

alertLogNormal                                  TRAP-TYPE
    ENTERPRISE  baseboardGroup
    VARIABLES { alertSystem,
                alertTableIndexOID,
                alertMessage,
                alertCurrentStatus,
                alertPreviousStatus,
                alertData }
    DESCRIPTION
"Log size is no longer near or at capacity."

    --Novell NMS trap annotation
    --#TYPE       "Server Hardware Log Normal"
    --#SUMMARY    "%s"
    --#ARGUMENTS  {2}
    --#SEVERITY   INFORMATIONAL
    --#TIMEINDEX  99
    --#STATE      OPERATIONAL

    ::= 1552

alertLogWarning                                 TRAP-TYPE
    ENTERPRISE  baseboardGroup
    VARIABLES { alertSystem,
                alertTableIndexOID,
                alertMessage,
                alertCurrentStatus,
                alertPreviousStatus,
                alertData }
    DESCRIPTION
"Log size is near capacity."

    --Novell NMS trap annotation
    --#TYPE       "Server Hardware Log Warning"
    --#SUMMARY    "%s"
    --#ARGUMENTS  {2}
    --#SEVERITY   MINOR
    --#TIMEINDEX  99
    --#STATE      OPERATIONAL

    ::= 1553

alertLogFull                                    TRAP-TYPE
    ENTERPRISE  baseboardGroup
    VARIABLES { alertSystem,
                alertTableIndexOID,
                alertMessage,
                alertCurrentStatus,
                alertPreviousStatus,
                alertData }
    DESCRIPTION
"Log size is at capacity."

    --Novell NMS trap annotation
    --#TYPE       "Server Hardware Log Full"
    --#SUMMARY    "%s"
    --#ARGUMENTS  {2}
    --#SEVERITY   CRITICAL
    --#TIMEINDEX  99
    --#STATE      DEGRADED

    ::= 1554

-------------------------------------------------------------------------------
-- Processor Device Status Traps
-------------------------------------------------------------------------------

alertProcessorDeviceStatusNormal                TRAP-TYPE
    ENTERPRISE  baseboardGroup
    VARIABLES { alertSystem,
                alertTableIndexOID,
                alertMessage,
                alertCurrentStatus,
                alertPreviousStatus,
                alertData }
    DESCRIPTION
"Processor device status has returned to normal."

    --Novell NMS trap annotation
    --#TYPE       "Server Processor Device Status Normal"
    --#SUMMARY    "%s"
    --#ARGUMENTS  {2}
    --#SEVERITY   INFORMATIONAL
    --#TIMEINDEX  99
    --#STATE      OPERATIONAL

    ::= 1602

alertProcessorDeviceStatusWarning               TRAP-TYPE
    ENTERPRISE  baseboardGroup
    VARIABLES { alertSystem,
                alertTableIndexOID,
                alertMessage,
                alertCurrentStatus,
                alertPreviousStatus,
                alertData }
    DESCRIPTION
"Processor device status has detected a warning."

    --Novell NMS trap annotation
    --#TYPE       "Server Processor Device Status Warning"
    --#SUMMARY    "%s"
    --#ARGUMENTS  {2}
    --#SEVERITY   MINOR
    --#TIMEINDEX  99
    --#STATE      DEGRADED

    ::= 1603

alertProcessorDeviceStatusFailure               TRAP-TYPE
    ENTERPRISE  baseboardGroup
    VARIABLES { alertSystem,
                alertTableIndexOID,
                alertMessage,
                alertCurrentStatus,
                alertPreviousStatus,
                alertData }
    DESCRIPTION
"Processor device status has detected a failure."

    --Novell NMS trap annotation
    --#TYPE       "Server Processor Device Status Failure"
    --#SUMMARY    "%s"
    --#ARGUMENTS  {2}
    --#SEVERITY   CRITICAL
    --#TIMEINDEX  99
    --#STATE      DEGRADED

    ::= 1604

-------------------------------------------------------------------------------
-- Device Traps
-------------------------------------------------------------------------------

alertDeviceAdd                                  TRAP-TYPE
    ENTERPRISE  baseboardGroup
    VARIABLES { alertSystem,
                alertTableIndexOID,
                alertMessage,
                alertCurrentStatus,
                alertPreviousStatus,
                alertData }
    DESCRIPTION
"Device added to system."

    --Novell NMS trap annotation
    --#TYPE       "Server Device Add"
    --#SUMMARY    "%s"
    --#ARGUMENTS  {2}
    --#SEVERITY   INFORMATIONAL
    --#TIMEINDEX  99
    --#STATE      OPERATIONAL

    ::= 1651

alertDeviceRemove                               TRAP-TYPE
    ENTERPRISE  baseboardGroup
    VARIABLES { alertSystem,
                alertTableIndexOID,
                alertMessage,
                alertCurrentStatus,
                alertPreviousStatus,
                alertData }
    DESCRIPTION
"Device removed from system."

    --Novell NMS trap annotation
    --#TYPE       "Server Device Remove"
    --#SUMMARY    "%s"
    --#ARGUMENTS  {2}
    --#SEVERITY   INFORMATIONAL
    --#TIMEINDEX  99
    --#STATE      OPERATIONAL

    ::= 1652

alertDeviceConfigError                          TRAP-TYPE
    ENTERPRISE  baseboardGroup
    VARIABLES { alertSystem,
                alertTableIndexOID,
                alertMessage,
                alertCurrentStatus,
                alertPreviousStatus,
                alertData }
    DESCRIPTION
"Device configuration error detected."

    --Novell NMS trap annotation
    --#TYPE       "Server Device Config Error"
    --#SUMMARY    "%s"
    --#ARGUMENTS  {2}
    --#SEVERITY   CRITICAL
    --#TIMEINDEX  99
    --#STATE      DEGRADED

    ::= 1653

-------------------------------------------------------------------------------
-- Battery Traps
-------------------------------------------------------------------------------

alertBatteryNormal                              TRAP-TYPE
    ENTERPRISE  baseboardGroup
    VARIABLES { alertSystem,
                alertTableIndexOID,
                alertMessage,
                alertCurrentStatus,
                alertPreviousStatus,
                alertData }
    DESCRIPTION
"Battery has returned to normal."

    --Novell NMS trap annotation
    --#TYPE       "Server Battery Normal"
    --#SUMMARY    "%s"
    --#ARGUMENTS  {2}
    --#SEVERITY   INFORMATIONAL
    --#TIMEINDEX  99
    --#STATE      OPERATIONAL

    ::= 1702

alertBatteryWarning                             TRAP-TYPE
    ENTERPRISE  baseboardGroup
    VARIABLES { alertSystem,
                alertTableIndexOID,
                alertMessage,
                alertCurrentStatus,
                alertPreviousStatus,
                alertData }
    DESCRIPTION
"Battery has detected a warning."

    --Novell NMS trap annotation
    --#TYPE       "Server Battery Warning"
    --#SUMMARY    "%s"
    --#ARGUMENTS  {2}
    --#SEVERITY   MINOR
    --#TIMEINDEX  99
    --#STATE      DEGRADED

    ::= 1703

alertBatteryFailure                             TRAP-TYPE
    ENTERPRISE  baseboardGroup
    VARIABLES { alertSystem,
                alertTableIndexOID,
                alertMessage,
                alertCurrentStatus,
                alertPreviousStatus,
                alertData }
    DESCRIPTION
"Battery has detected a failure."

    --Novell NMS trap annotation
    --#TYPE       "Server Battery Failure"
    --#SUMMARY    "%s"
    --#ARGUMENTS  {2}
    --#SEVERITY   CRITICAL
    --#TIMEINDEX  99
    --#STATE      DEGRADED

    ::= 1704

-------------------------------------------------------------------------------
-- SD Card Device Traps
-------------------------------------------------------------------------------

alertSDCardDeviceFailure                        TRAP-TYPE
    ENTERPRISE  baseboardGroup
    VARIABLES { alertSystem,
                alertTableIndexOID,
                alertMessage,
                alertCurrentStatus,
                alertPreviousStatus,
                alertData }
    DESCRIPTION
"SD card device has detected a failure."

    --Novell NMS trap annotation
    --#TYPE       "Server SD Card Device Failure"
    --#SUMMARY    "%s"
    --#ARGUMENTS  {2}
    --#SEVERITY   CRITICAL
    --#TIMEINDEX  99
    --#STATE      DEGRADED

    ::= 1754


END

-------------------------------------------------------------------------------
-- End MIB
-------------------------------------------------------------------------------
